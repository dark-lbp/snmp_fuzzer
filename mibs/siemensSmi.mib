-- ----------------------------------------------------------------------
-- siemensSmi.mib
--
-- SIEMENS AG 
-- Industry Sector
--     
-- Siemens Structure of Management Information
--
-- Copyright (c) 2005-2008 Siemens AG
-- All rights reserved.
-- ----------------------------------------------------------------------
      
SIEMENS-SMI           DEFINITIONS ::= BEGIN

IMPORTS       
  MODULE-IDENTITY,
  enterprises           FROM SNMPv2-SMI;

siemens                 MODULE-IDENTITY
  LAST-UPDATED          "200811100000Z"
  ORGANIZATION          "Siemens AG"
  CONTACT-INFO          "
                         Siemens AG
                         Industry Sector
                         I IA SC IC RD 5
                         Ingo Landgraf

                         Postal: Gleiwitzer Strasse 555
                                 Nuremberg-Moorenbrunn
                                 D-90475
                         Tel:    +49 911 895 3765
                         E-mail: ingo.landgraf@siemens.com
                        "
  DESCRIPTION           "
                        The root object identifier of Siemens. The
                        MIB module provides the structure of
                        management information of Siemens AG.
                        "

  REVISION              "200811100000Z"
  DESCRIPTION           "Update the contact information."

  REVISION              "200806020000Z"
  DESCRIPTION           "Initial Version of the MIB module."
  ::= { enterprises 4329 }

END
