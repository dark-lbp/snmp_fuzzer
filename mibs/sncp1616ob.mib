-- ----------------------------------------------------------------------
-- snCP1616Onboard.mib
-- Siemens  SIMATIC NET 
-- CP1616 onboard Private MIB
-- Copyright (c) 2004 Siemens AG
-- ----------------------------------------------------------------------
--
-- MIB Module :   SN-CP1616-ONBOARD-PRIV-MIB
--
-- Revision   :   V0.1.0
-- Date       :   2007/05/08 
--
-- ----------------------------------------------------------------------

SN-CP1616-ONBOARD-PRIV-MIB DEFINITIONS ::= BEGIN

  IMPORTS
          enterprises FROM RFC1155-SMI
          OBJECT-TYPE FROM RFC-1212;

  DisplayString ::=
    OCTET STRING

siemensAD               OBJECT IDENTIFIER ::= { enterprises 4196 }
adProductMibs           OBJECT IDENTIFIER ::= { siemensAD 1 }
simaticNet              OBJECT IDENTIFIER ::= { adProductMibs 1 }
iCP       	            OBJECT IDENTIFIER ::= { simaticNet 9 } 
iCP1616Onboard          OBJECT IDENTIFIER ::= { iCP 5 } 

-- -------------------------------------------------------------
-- SIMATIC NET CP1616 ONBOARD Objects
-- -------------------------------------------------------------
snCommon             OBJECT IDENTIFIER ::= { iCP1616Onboard 1 }
snProductSpecific    OBJECT IDENTIFIER ::= { iCP1616Onboard 2 }


-- -------------------------------------------------------------
-- SIMATIC NET CP1616 ONBOARD Report Objects
-- -------------------------------------------------------------
snCP1616OnboardReport        OBJECT IDENTIFIER ::= { snProductSpecific 2 }


-- --------------------------------------------------------------
-- SIMATIC NET CP1616 ONBOARD Report Group
-- --------------------------------------------------------------
snCP1616OnboardBFLedVal OBJECT-TYPE
   SYNTAX INTEGER { off(1), on(2), blink(3), fastBlink(4) }
   ACCESS read-only
   STATUS mandatory
   DESCRIPTION "State of BF LED. Value list: off(1), on(2), blink(3), fastBlink(4)"
   ::= { snCP1616OnboardReport 1 }

snCP1616OnboardSFLedVal OBJECT-TYPE
   SYNTAX INTEGER { off(1), on(2), blink(3), fastBlink(4) }
   ACCESS read-only
   STATUS mandatory
   DESCRIPTION "State of SF LED. Value list: off(1), on(2), blink(3), fastBlink(4)"
   ::= { snCP1616OnboardReport 2 }

snCP1616OnboardRunLedVal OBJECT-TYPE
   SYNTAX INTEGER { off(1), on(2), blink(3), fastBlink(4) }
   ACCESS read-only
   STATUS mandatory
   DESCRIPTION "State of run LED. Value list: off(1), on(2), blink(3), fastBlink(4)"
   ::= { snCP1616OnboardReport 3 }

snCP1616OnboardStopLedVal OBJECT-TYPE
   SYNTAX INTEGER { off(1), on(2), blink(3), fastBlink(4) }
   ACCESS read-only
   STATUS mandatory
   DESCRIPTION "State of stop LED. Value list: off(1), on(2), blink(3), fastBlink(4)"
   ::= { snCP1616OnboardReport 4 }

snCP1616OnboardBFLed OBJECT-TYPE
   SYNTAX  DisplayString (SIZE (0..255))
   ACCESS read-only
   STATUS mandatory
   DESCRIPTION "Textual description of the BF LED state"
   ::= { snCP1616OnboardReport 5 }

snCP1616OnboardSFLed OBJECT-TYPE
   SYNTAX  DisplayString (SIZE (0..255))
   ACCESS read-only
   STATUS mandatory
   DESCRIPTION "Textual description of the SF LED state"
   ::= { snCP1616OnboardReport 6 }

snCP1616OnboardRunLed OBJECT-TYPE
   SYNTAX  DisplayString (SIZE (0..255))
   ACCESS read-only
   STATUS mandatory
   DESCRIPTION "Textual description of the run LED state"
   ::= { snCP1616OnboardReport 7 }

snCP1616OnboardStopLed OBJECT-TYPE
   SYNTAX  DisplayString (SIZE (0..255))
   ACCESS read-only
   STATUS mandatory
   DESCRIPTION "Textual description of the stop LED state"
   ::= { snCP1616OnboardReport 8 }

END
