-- MIB generated by miftomib version 1.0a

-- MIB file version number 7.00-15

MYLEXRAID-MIB DEFINITIONS ::= BEGIN

-- Mylex Disk Array Controller

IMPORTS
    OBJECT-TYPE
    FROM RFC-1212
    Counter, enterprises
    FROM RFC1155-SMI
    DisplayString
    FROM RFC1213-MIB;

DmiCounter			::= Counter
DmiInteger			::= INTEGER
DmiDisplaystring	::= DisplayString
DmiDate				::= OCTET STRING (SIZE (28))
DmiComponentIndex	::= INTEGER

mylex               	OBJECT IDENTIFIER ::= {enterprises 1608}
dmtfStd             	OBJECT IDENTIFIER ::= {mylex 1}
dmtfComponents      	OBJECT IDENTIFIER ::= {dmtfStd 1}
dmtfGroups          	OBJECT IDENTIFIER ::= {dmtfComponents 1}



tControllerInformation OBJECT-TYPE
	SYNTAX		SEQUENCE OF SControllerInformation
	ACCESS		not-accessible
	STATUS		mandatory
	DESCRIPTION	"This group provides Controller Information."
	::= {dmtfGroups 2}

eControllerInformation OBJECT-TYPE
	SYNTAX		SControllerInformation
	ACCESS		not-accessible
	STATUS		mandatory
	DESCRIPTION	""
	INDEX		{a2ControllerNumber}
	::= {tControllerInformation 1}

a2ControllerNumber OBJECT-TYPE
	SYNTAX		DmiInteger
	ACCESS		read-only
	STATUS		mandatory
	DESCRIPTION	"Controller Number assigned to this controller by the device
driver."
	::= {eControllerInformation 1}

a2OperationalState OBJECT-TYPE
	SYNTAX		INTEGER {
		vFunctional                             	(1),
		vNon-functional                         	(2),
		vNotPresent                             	(128)
	}
	ACCESS		read-only
	STATUS		mandatory
	DESCRIPTION	"Operational state of this controller as seen by the device
driver."
	::= {eControllerInformation 2}

a2FirmwareRevision OBJECT-TYPE
	SYNTAX		DmiDisplaystring
	ACCESS		read-only
	STATUS		mandatory
	DESCRIPTION	"Controller Firmware Revision."
	::= {eControllerInformation 3}

a2ConfiguredChannels OBJECT-TYPE
	SYNTAX		DmiInteger
	ACCESS		read-only
	STATUS		mandatory
	DESCRIPTION	"Number of Channels that are part of controller configuration."
	::= {eControllerInformation 4}

a2ActualChannels OBJECT-TYPE
	SYNTAX		DmiInteger
	ACCESS		read-only
	STATUS		mandatory
	DESCRIPTION	"Number of Channels that are physically present on-board the
controller."
	::= {eControllerInformation 5}

a2MaximumLogicalDrives OBJECT-TYPE
	SYNTAX		DmiInteger
	ACCESS		read-only
	STATUS		mandatory
	DESCRIPTION	"Maximum number of logical drives that can be configured on
this controller."
	::= {eControllerInformation 6}

a2MaximumTargetsPerChannel OBJECT-TYPE
	SYNTAX		DmiInteger
	ACCESS		read-only
	STATUS		mandatory
	DESCRIPTION	"Maximum Number of Physical Target IDs supported per Channel"
	::= {eControllerInformation 7}

a2MaximumTaggedRequests OBJECT-TYPE
	SYNTAX		DmiInteger
	ACCESS		read-only
	STATUS		mandatory
	DESCRIPTION	"Maximum Number of Tagged requests that may be sent to a Hard
disk device by Controller Firmware."
	::= {eControllerInformation 8}

a2MaximumDataTransferSizePerIoRequestInK OBJECT-TYPE
	SYNTAX		DmiInteger
	ACCESS		read-only
	STATUS		mandatory
	DESCRIPTION	"Maximum amount of data that can be transferred per a single
IO request - in KB."
	::= {eControllerInformation 9}

a2MaximumConcurrentCommands OBJECT-TYPE
	SYNTAX		DmiInteger
	ACCESS		read-only
	STATUS		mandatory
	DESCRIPTION	"Maximum number of requests that can be sent to the controller
simultaneouly."
	::= {eControllerInformation 10}

a2RebuildRate OBJECT-TYPE
	SYNTAX		DmiInteger
	ACCESS		read-only
	STATUS		mandatory
	DESCRIPTION	"Value of Rebuild Rate."
	::= {eControllerInformation 11}

a2LogicalSectorSizeInBytes OBJECT-TYPE
	SYNTAX		DmiInteger
	ACCESS		read-only
	STATUS		mandatory
	DESCRIPTION	"Logical Sector Size in Bytes (Default: 512 bytes)."
	::= {eControllerInformation 12}

a2PhysicalSectorSizeInBytes OBJECT-TYPE
	SYNTAX		DmiInteger
	ACCESS		read-only
	STATUS		mandatory
	DESCRIPTION	"Physical Sector Size in Bytes (Default: 512 bytes)."
	::= {eControllerInformation 13}

a2CacheLineSizeInBytes OBJECT-TYPE
	SYNTAX		DmiInteger
	ACCESS		read-only
	STATUS		mandatory
	DESCRIPTION	"Cache Line Size in Bytes."
	::= {eControllerInformation 14}

a2CacheSizeInMb OBJECT-TYPE
	SYNTAX		DmiInteger
	ACCESS		read-only
	STATUS		mandatory
	DESCRIPTION	"Size of Controller Cache Module - in MB."
	::= {eControllerInformation 15}



a2CacheMemoryType OBJECT-TYPE
	SYNTAX		INTEGER {
		vDram                                   	(1),
		vEdram                                  	(2),
		vEdo                                    	(3),
		vSdram                                  	(4),
		vDram-parity                            	(65),
		vEdram-parity                           	(66),
		vEdo-parity                             	(67),
		vSdram-parity                           	(68),
		vDram-ecc                               	(129),
		vEdram-ecc                              	(130),
		vEdo-ecc                                	(131),
		vSdram-ecc                              	(132),
		vUnknown                                	(255)
	}
	ACCESS		read-only
	STATUS		mandatory
	DESCRIPTION	"Controller Cache Memory Type."
	::= {eControllerInformation 16}

a2EpromSizeInKb OBJECT-TYPE
	SYNTAX		DmiInteger
	ACCESS		read-only
	STATUS		mandatory
	DESCRIPTION	"Size of Controller EPROM Module - in KB."
	::= {eControllerInformation 17}

a2BusType OBJECT-TYPE
	SYNTAX		INTEGER {
		vEisa                                   	(1),
		vMca                                    	(2),
		vPci                                    	(3),
		vVesa                                   	(4),
		vIsa                                    	(5),
		vPCIX						(7), 
		vPCIE						(8), 
		vUnknown                                	(255)
	}
	ACCESS		read-only
	STATUS		mandatory
	DESCRIPTION	"Controller - System Bus Interface Type."
	::= {eControllerInformation 18}

a2ControllerClass OBJECT-TYPE
	SYNTAX		INTEGER {
		vRaid                                   	(1),
		vMegaraid                               	(128),
		vUnknown                                	(255)
	}
	ACCESS		read-only
	STATUS		mandatory
	DESCRIPTION	"Controller Class Type."
	::= {eControllerInformation 19}

a2ControllerModel OBJECT-TYPE
	SYNTAX		INTEGER {
		vDac960e                                	(1),
		vDac960m                                	(8),
		vDac960pd                               	(16),
		vDac960pl                               	(17),
		vDac960pdu                              	(18),
		vDac960pe                               	(19),
		vDac960pg                               	(20),
		vDac960pj                               	(21),
		vDac960ptl0                             	(22),
		vDac960pr                               	(23),
		vDac960prl                              	(24),
		vDac960pt                               	(25),
		vDac1164p                               	(26),
		vDac960ptl1                             	(27),
		vExtremeraid2000                        	(28),
		vExtremeraid3000                        	(29),
		vAcceleraid352                          	(30),
		vAcceleraid170                          	(31),
		vAcceleraid160                          	(32),
		vExtremeraid4000                        	(35),
		vExtremeraid5000                        	(36),
		vAcceleraid500                          	(37),
		vAcceleraid400                          	(38),
		vDac960s                                	(96),
		vDac960su                               	(97),
		vDac960sx                               	(98),
		vDac960sf                               	(99),
		vDac960ss                               	(100),
		vDac960fl                               	(101),
		vDac960ll                               	(102),
		vDac960ff                               	(103),
		vFcarray                                	(104),
		vDac960mfl                              	(105),
		vDac960mff                              	(106),
		vDacffx                                 	(107),
		vDacffx2                                	(109),
		vMegaraidscsi320-1                      	(128),
		vMegaraidscsi320-2                      	(129),
		vMegaraidscsi320-4x                     	(130),
		vMegaraidscsi320-2x                     	(131),
		vMegaraidscsi320-roc                    	(132),
		vMegaraidscsi320-zcr0                   	(133),
		vMegaraidscsi320-zcr0x                  	(134),
		vMegaraidscsi320-2e                     	(135),
		vMegaRAIDSAS8408E							(217),
		vMegaRAIDSASPCIExpressROMB					(218),
		vMegaRAIDSAS8344ELP							(219),
		vMegaRAIDSAS8480E							(220),
		vMegaRAIDSAS8308ELP							(221),
		vMegaRAIDSATA3008ELP						(222),
		vMegaRAIDSAS8300XLP							(223),
		vMegaRAIDSAS8808E							(224),
		vMegaRAIDSAS8608E							(225),
		vMegaRAIDSAS8208XLP							(226),
		vMegaRAIDSAS8208ELP							(227),
		vLSI1068SASIME								(234),
		vSAS3442X									(235),
		v1068SASIME-2107							(236),
		v1068SASIME-2300							(237),
		v1068SASIME-2129							(238),
		v1068SASIME-2119							(239),
		v1068SASIME-2280							(240),
		v1068SASIME-2532							(241),
		v1068SASIME-2399							(242),
		v1068SASIME-2003							(243),
		vFSCEmbeddedServerRAID						(251),
		vLSILogicEmbeddedMegaRAID					(252),
		vUnknown                                	(255)
	}
	ACCESS		read-only
	STATUS		mandatory
	DESCRIPTION	"Controller Model Type."
	::= {eControllerInformation 20}

a2SystemBusNumber OBJECT-TYPE
	SYNTAX		DmiInteger
	ACCESS		read-only
	STATUS		mandatory
	DESCRIPTION	"System Bus Number, for the bus the controller is interfacing
with. This value is supplied by the Operating system and may not be defined
for all operating systems."
	::= {eControllerInformation 21}

a2SlotNumber OBJECT-TYPE
	SYNTAX		DmiInteger
	ACCESS		read-only
	STATUS		mandatory
	DESCRIPTION	"Slot Number where the controller is physically present. Defined
for EISA and MCA controller only. "
	::= {eControllerInformation 22}

a2InterruptVectorNumber OBJECT-TYPE
	SYNTAX		DmiInteger
	ACCESS		read-only
	STATUS		mandatory
	DESCRIPTION	"Interrupt Vector Number being used by the controller. This
value is a mapped IRQ supplied by Operating System and may not be same as
the actual Interrupt Vector."
	::= {eControllerInformation 23}

a2InterruptMode OBJECT-TYPE
	SYNTAX		INTEGER {
		vEdge                                   	(0),
		vLevel                                  	(1),
		vUnknown                                	(255)
	}
	ACCESS		read-only
	STATUS		mandatory
	DESCRIPTION	"Interrupt Mode - Edge/Level."
	::= {eControllerInformation 24}

a2NumberOfPhysicalDevices OBJECT-TYPE
	SYNTAX		DmiInteger
	ACCESS		read-only
	STATUS		mandatory
	DESCRIPTION	"Number Of Physical Devices detected on this controller."
	::= {eControllerInformation 25}

a2NumberOfPhysicalDevicesOffline OBJECT-TYPE
	SYNTAX		DmiInteger
	ACCESS		read-only
	STATUS		mandatory
	DESCRIPTION	"Number of Physical Devices, whose operational state is Offline."
	::= {eControllerInformation 26}

a2NumberOfLogicalDevices OBJECT-TYPE
	SYNTAX		DmiInteger
	ACCESS		read-only
	STATUS		mandatory
	DESCRIPTION	"Number of Logical Devices currently configured."
	::= {eControllerInformation 27}

a2NumberOfLogicalDevicesCritical OBJECT-TYPE
	SYNTAX		DmiInteger
	ACCESS		read-only
	STATUS		mandatory
	DESCRIPTION	"Number of Logical Devices, whose operational state is Critical."
	::= {eControllerInformation 28}

a2NumberOfLogicalDevicesOffline OBJECT-TYPE
	SYNTAX		DmiInteger
	ACCESS		read-only
	STATUS		mandatory
	DESCRIPTION	"Number of Logical Devices, whose operational state is Offline."
	::= {eControllerInformation 29}

a2FaultManagementType OBJECT-TYPE
	SYNTAX		INTEGER {
		vNotPresent                             	(0),
		vAemi                                   	(1),
		vOem1                                   	(2),
		vOem2                                   	(4),
		vOem3                                   	(8),
		vConner                                 	(16),
		vSafte                                  	(32),
		vSes                                    	(64)
	}
	ACCESS		read-only
	STATUS		mandatory
	DESCRIPTION	"Controller Fault Management Type."
	::= {eControllerInformation 30}

a2ArrayInformation OBJECT-TYPE
	SYNTAX		DmiDisplaystring
	ACCESS		read-only
	STATUS		mandatory
	DESCRIPTION	"Information about Array(s) definition. The information is
provided in Channel-Target combination form."
	::= {eControllerInformation 31}

a2LogicalDriveReadRequests OBJECT-TYPE
	SYNTAX		DmiCounter
	ACCESS		read-only
	STATUS		mandatory
	DESCRIPTION	"Number of Read Requests to Logical Drives."
	::= {eControllerInformation 32}

a2DataReadFromLogicalDrivesInMb OBJECT-TYPE
	SYNTAX		DmiInteger
	ACCESS		read-only
	STATUS		mandatory
	DESCRIPTION	"Amount of Data Read from all Logical Drives - in MB."
	::= {eControllerInformation 33}

a2LogicalDriveWriteRequests OBJECT-TYPE
	SYNTAX		DmiCounter
	ACCESS		read-only
	STATUS		mandatory
	DESCRIPTION	"Number of Write Requests to Logical Drives."
	::= {eControllerInformation 34}

a2DataWrittenToLogicalDrivesInMb OBJECT-TYPE
	SYNTAX		DmiInteger
	ACCESS		read-only
	STATUS		mandatory
	DESCRIPTION	"Amount of data written to all Logical Drives - in MB."
	::= {eControllerInformation 35}

a2LogicalDrivesReadCacheHitPercentage OBJECT-TYPE
	SYNTAX		DmiInteger
	ACCESS		read-only
	STATUS		mandatory
	DESCRIPTION	"Logical Drives Read Data Cache Hit Rate."
	::= {eControllerInformation 36}

a2PhysicalDriveReadRequests OBJECT-TYPE
	SYNTAX		DmiCounter
	ACCESS		read-only
	STATUS		mandatory
	DESCRIPTION	"Number of Read Requests to all physical drives."
	::= {eControllerInformation 37}

a2DataReadFromPhysicalDrivesInMb OBJECT-TYPE
	SYNTAX		DmiInteger
	ACCESS		read-only
	STATUS		mandatory
	DESCRIPTION	"Amount of Data Read from all physical drives - in MB."
	::= {eControllerInformation 38}

a2PhysicalDriveWriteRequests OBJECT-TYPE
	SYNTAX		DmiCounter
	ACCESS		read-only
	STATUS		mandatory
	DESCRIPTION	"Number of Write Requests to all physical drives on this controll
r."
	::= {eControllerInformation 39}

a2DataWrittenToPhysicalDrivesInMb OBJECT-TYPE
	SYNTAX		DmiInteger
	ACCESS		read-only
	STATUS		mandatory
	DESCRIPTION	"Amount of data written all physical drives on this controller-
in MB."
	::= {eControllerInformation 40}

a2StorageworksCabinetStatusOnChannel0 OBJECT-TYPE
	SYNTAX		INTEGER {
		vOk                                     	(1),
		vNotOk                                  	(2),
		vNotPresent                             	(3)
	}
	ACCESS		read-only
	STATUS		mandatory
	DESCRIPTION	"StorageWorks Cabinet Status on Channel 0"
	::= {eControllerInformation 41}

a2StorageworksCabinetStatusOnChannel1 OBJECT-TYPE
	SYNTAX		INTEGER {
		vOk                                     	(1),
		vNotOk                                  	(2),
		vNotPresent                             	(3)
	}
	ACCESS		read-only
	STATUS		mandatory
	DESCRIPTION	"StorageWorks Cabinet Status on Channel 1"
	::= {eControllerInformation 42}

a2StorageworksCabinetStatusOnChannel2 OBJECT-TYPE
	SYNTAX		INTEGER {
		vOk                                     	(1),
		vNotOk                                  	(2),
		vNotPresent                             	(3)
	}
	ACCESS		read-only
	STATUS		mandatory
	DESCRIPTION	"StorageWorks Cabinet Status on Channel 2"
	::= {eControllerInformation 43}

a2BatteryBackupUnitStatus OBJECT-TYPE
	SYNTAX		INTEGER {
		vNotPresent                             	(0),
		vPresent                                	(1)
	}
	ACCESS		read-only
	STATUS		mandatory
	DESCRIPTION	"Battery Backup Unit Status."
	::= {eControllerInformation 44}

a2PartnerControllerNumber OBJECT-TYPE
	SYNTAX		DmiInteger
	ACCESS		read-only
	STATUS		mandatory
	DESCRIPTION	"Controller Number of the Partner Controller."
	::= {eControllerInformation 45}

a2WwName OBJECT-TYPE
	SYNTAX		DmiDisplaystring
	ACCESS		read-only
	STATUS		mandatory
	DESCRIPTION	"Controller World Wide Name."
	::= {eControllerInformation 46}

a2HostControllerNumber OBJECT-TYPE
	SYNTAX		DmiInteger
	ACCESS		read-only
	STATUS		mandatory
	DESCRIPTION	"Host Controller Number."
	::= {eControllerInformation 47}

a2HostChannelNumber OBJECT-TYPE
	SYNTAX		DmiInteger
	ACCESS		read-only
	STATUS		mandatory
	DESCRIPTION	"Host Channel Number."
	::= {eControllerInformation 48}

a2HostTargetId OBJECT-TYPE
	SYNTAX		DmiInteger
	ACCESS		read-only
	STATUS		mandatory
	DESCRIPTION	"Host Target ID."
	::= {eControllerInformation 49}

SControllerInformation ::= SEQUENCE {
	a2ControllerNumber                      	DmiInteger,
	a2OperationalState                      	DmiInteger,
	a2FirmwareRevision                      	DmiDisplaystring,
	a2ConfiguredChannels                    	DmiInteger,
	a2ActualChannels                        	DmiInteger,
	a2MaximumLogicalDrives                  	DmiInteger,
	a2MaximumTargetsPerChannel              	DmiInteger,
	a2MaximumTaggedRequests                 	DmiInteger,
	a2MaximumDataTransferSizePerIoRequestInK	DmiInteger,
	a2MaximumConcurrentCommands             	DmiInteger,
	a2RebuildRate                           	DmiInteger,
	a2LogicalSectorSizeInBytes              	DmiInteger,
	a2PhysicalSectorSizeInBytes             	DmiInteger,
	a2CacheLineSizeInBytes                  	DmiInteger,
	a2CacheSizeInMb                         	DmiInteger,
	a2CacheMemoryType                       	DmiInteger,
	a2EpromSizeInKb                         	DmiInteger,
	a2BusType                               	DmiInteger,
	a2ControllerClass                       	DmiInteger,
	a2ControllerModel                       	DmiInteger,
	a2SystemBusNumber                       	DmiInteger,
	a2SlotNumber                            	DmiInteger,
	a2InterruptVectorNumber                 	DmiInteger,
	a2InterruptMode                         	DmiInteger,
	a2NumberOfPhysicalDevices               	DmiInteger,
	a2NumberOfPhysicalDevicesOffline        	DmiInteger,
	a2NumberOfLogicalDevices                	DmiInteger,
	a2NumberOfLogicalDevicesCritical        	DmiInteger,
	a2NumberOfLogicalDevicesOffline         	DmiInteger,
	a2FaultManagementType                   	DmiInteger,
	a2ArrayInformation                      	DmiDisplaystring,
	a2LogicalDriveReadRequests              	DmiCounter,
	a2DataReadFromLogicalDrivesInMb         	DmiInteger,
	a2LogicalDriveWriteRequests             	DmiCounter,
	a2DataWrittenToLogicalDrivesInMb        	DmiInteger,
	a2LogicalDrivesReadCacheHitPercentage   	DmiInteger,
	a2PhysicalDriveReadRequests             	DmiCounter,
	a2DataReadFromPhysicalDrivesInMb        	DmiInteger,
	a2PhysicalDriveWriteRequests            	DmiCounter,
	a2DataWrittenToPhysicalDrivesInMb       	DmiInteger,
	a2StorageworksCabinetStatusOnChannel0   	DmiInteger,
	a2StorageworksCabinetStatusOnChannel1   	DmiInteger,
	a2StorageworksCabinetStatusOnChannel2   	DmiInteger,
	a2BatteryBackupUnitStatus               	DmiInteger,
	a2PartnerControllerNumber               	DmiInteger,
	a2WwName                                	DmiDisplaystring,
	a2HostControllerNumber                  	DmiInteger,
	a2HostChannelNumber                     	DmiInteger,
	a2HostTargetId                          	DmiInteger
}




tLogicalDriveInformation OBJECT-TYPE
	SYNTAX		SEQUENCE OF SLogicalDriveInformation
	ACCESS		not-accessible
	STATUS		mandatory
	DESCRIPTION	"Provides information about Logical Drive Configuration."
	::= {dmtfGroups 3}

eLogicalDriveInformation OBJECT-TYPE
	SYNTAX		SLogicalDriveInformation
	ACCESS		not-accessible
	STATUS		mandatory
	DESCRIPTION	""
	INDEX		{a3ControllerNumber, a3LogicalDriveNumber}
	::= {tLogicalDriveInformation 1}

a3ControllerNumber OBJECT-TYPE
	SYNTAX		DmiInteger
	ACCESS		read-only
	STATUS		mandatory
	DESCRIPTION	"Controller Number - used as a key."
	::= {eLogicalDriveInformation 1}

a3LogicalDriveNumber OBJECT-TYPE
	SYNTAX		DmiInteger
	ACCESS		read-only
	STATUS		mandatory
	DESCRIPTION	"Logical Drive Number - used as a Key."
	::= {eLogicalDriveInformation 2}

a3OperationalState OBJECT-TYPE
	SYNTAX		INTEGER {
		vOnline                                 	(3),
		vCritical                               	(4),
		vNotPresent                             	(128),
		vOffline                                	(255)
	}
	ACCESS		read-only
	STATUS		mandatory
	DESCRIPTION	"Logical Drive Operational State."
	::= {eLogicalDriveInformation 3}

a3RaidLevel OBJECT-TYPE
	SYNTAX		DmiInteger
	ACCESS		read-only
	STATUS		mandatory
	DESCRIPTION	"RAID Level associated with Logical Drive."
	::= {eLogicalDriveInformation 4}

a3WritePolicy OBJECT-TYPE
	SYNTAX		INTEGER {
		vWriteThru                              	(0),
		vWriteBack                              	(128)
	}
	ACCESS		read-only
	STATUS		mandatory
	DESCRIPTION	"Write Cache Policy associated with Logical Drive."
	::= {eLogicalDriveInformation 5}

a3SizeInMb OBJECT-TYPE
	SYNTAX		DmiInteger
	ACCESS		read-only
	STATUS		mandatory
	DESCRIPTION	"Logical Drive Size - in MB."
	::= {eLogicalDriveInformation 6}

a3PhysicalSizeInMb OBJECT-TYPE
	SYNTAX		DmiInteger
	ACCESS		read-only
	STATUS		mandatory
	DESCRIPTION	"Total physical capacity used by this Logical Drive - in MB."
	::= {eLogicalDriveInformation 7}

a3StripeSizeInBytes OBJECT-TYPE
	SYNTAX		DmiInteger
	ACCESS		read-only
	STATUS		mandatory
	DESCRIPTION	"Stripe size associated with Logical Drive. Valid for RAID
Levels 0, 5 and 6 only. Value is specifed in bytes."
	::= {eLogicalDriveInformation 8}

a3PhysicalDriveMap OBJECT-TYPE
	SYNTAX		DmiDisplaystring
	ACCESS		read-only
	STATUS		mandatory
	DESCRIPTION	"List of all physical drives that make up this Logical Drive.
The information is provided in Channel-Target combination form."
	::= {eLogicalDriveInformation 9}

a3ArrayList OBJECT-TYPE
	SYNTAX		DmiDisplaystring
	ACCESS		read-only
	STATUS		mandatory
	DESCRIPTION	"List of Arrays, this logical drive spans across. "
	::= {eLogicalDriveInformation 10}

a3RaidLevelString OBJECT-TYPE
	SYNTAX		DmiDisplaystring
	ACCESS		read-only
	STATUS		mandatory
	DESCRIPTION	"Raid Level String."
	::= {eLogicalDriveInformation 11}

SLogicalDriveInformation ::= SEQUENCE {
	a3ControllerNumber                      	DmiInteger,
	a3LogicalDriveNumber                    	DmiInteger,
	a3OperationalState                      	DmiInteger,
	a3RaidLevel                             	DmiInteger,
	a3WritePolicy                           	DmiInteger,
	a3SizeInMb                              	DmiInteger,
	a3PhysicalSizeInMb                      	DmiInteger,
	a3StripeSizeInBytes                     	DmiInteger,
	a3PhysicalDriveMap                      	DmiDisplaystring,
	a3ArrayList                             	DmiDisplaystring,
	a3RaidLevelString                       	DmiDisplaystring
}



tPhysicalDeviceInformation OBJECT-TYPE
	SYNTAX		SEQUENCE OF SPhysicalDeviceInformation
	ACCESS		not-accessible
	STATUS		mandatory
	DESCRIPTION	"SCSI Physical Device Information."
	::= {dmtfGroups 4}

ePhysicalDeviceInformation OBJECT-TYPE
	SYNTAX		SPhysicalDeviceInformation
	ACCESS		not-accessible
	STATUS		mandatory
	DESCRIPTION	""
	INDEX		{a4ControllerNumber, a4ChannelNumber, a4TargetId}
	::= {tPhysicalDeviceInformation 1}

a4ControllerNumber OBJECT-TYPE
	SYNTAX		DmiInteger
	ACCESS		read-only
	STATUS		mandatory
	DESCRIPTION	"Controller Number - used as a key"
	::= {ePhysicalDeviceInformation 1}

a4ChannelNumber OBJECT-TYPE
	SYNTAX		DmiInteger
	ACCESS		read-only
	STATUS		mandatory
	DESCRIPTION	"Channel Number - used as a key"
	::= {ePhysicalDeviceInformation 2}

a4TargetId OBJECT-TYPE
	SYNTAX		DmiInteger
	ACCESS		read-only
	STATUS		mandatory
	DESCRIPTION	"Physical Device Target Id - used as a key"
	::= {ePhysicalDeviceInformation 3}

a4Lun OBJECT-TYPE
	SYNTAX		DmiInteger
	ACCESS		read-only
	STATUS		mandatory
	DESCRIPTION	"LUN of the Physical Device."
	::= {ePhysicalDeviceInformation 4}

a4OperationalState OBJECT-TYPE
	SYNTAX		INTEGER {
		vDead                                   	(0),
		vRebuilding                             	(2),
		vOnline                                 	(3),
		vInstallationAbort                      	(4),
		vPresent                                	(5),
		vNotPresent                             	(6),
		vHotspare                               	(16),
		vRebuildCancelled                       	(130),
		vDedicatedHotspare                      	(97)
	}
	ACCESS		read-only
	STATUS		mandatory
	DESCRIPTION	"Physical Device State."
	::= {ePhysicalDeviceInformation 5}

a4VendorId OBJECT-TYPE
	SYNTAX		DmiDisplaystring
	ACCESS		read-only
	STATUS		mandatory
	DESCRIPTION	"Physical Device Vendor Id."
	::= {ePhysicalDeviceInformation 6}

a4ProductId OBJECT-TYPE
	SYNTAX		DmiDisplaystring
	ACCESS		read-only
	STATUS		mandatory
	DESCRIPTION	"Physical Device Product Id."
	::= {ePhysicalDeviceInformation 7}

a4ProductRevisionLevel OBJECT-TYPE
	SYNTAX		DmiDisplaystring
	ACCESS		read-only
	STATUS		mandatory
	DESCRIPTION	"Physical Device Product Revision Level."
	::= {ePhysicalDeviceInformation 8}

a4SizeInMb OBJECT-TYPE
	SYNTAX		DmiInteger
	ACCESS		read-only
	STATUS		mandatory
	DESCRIPTION	"Physcical Capacity in MB, valid for physical drive only."
	::= {ePhysicalDeviceInformation 9}

a4DeviceType OBJECT-TYPE
	SYNTAX		INTEGER {
		vFixedDrive                             	(0),
		vTape                                   	(1),
		vPrinter                                	(2),
		vProcessor                              	(3),
		vWorm                                   	(4),
		vCdrom                                  	(5),
		vScanner                                	(6),
		vMo                                     	(7),
		vChanger                                	(8),
		vCommunications                         	(9),
		vGraphics-0                             	(10),
		vGraphics-1                             	(11),
		vReserved-0                             	(12),
		vReserved-1                             	(13),
		vReserved-2                             	(14),
		vReserved-3                             	(15),
		vReserved-4                             	(16),
		vReserved-5                             	(17),
		vReserved-6                             	(18),
		vReserved-7                             	(19),
		vReserved-8                             	(20),
		vReserved-9                             	(21),
		vReserved-10                            	(22),
		vReserved-11                            	(23),
		vReserved-12                            	(24),
		vReserved-13                            	(25),
		vReserved-14                            	(26),
		vReserved-15                            	(27),
		vReserved-16                            	(28),
		vReserved-17                            	(29),
		vReserved-18                            	(30),
		vUnknown                                	(31),
		vScsiHostBusAdapter                     	(199),
		vCtrlChannel                            	(204)
	}
	ACCESS		read-only
	STATUS		mandatory
	DESCRIPTION	"Device Type."
	::= {ePhysicalDeviceInformation 10}

a4SoftErrors OBJECT-TYPE
	SYNTAX		DmiInteger
	ACCESS		read-only
	STATUS		mandatory
	DESCRIPTION	"Number of Soft Errors, valid for physical drive only."
	::= {ePhysicalDeviceInformation 11}

a4HardErrors OBJECT-TYPE
	SYNTAX		DmiCounter
	ACCESS		read-only
	STATUS		mandatory
	DESCRIPTION	"Number of Hard Errors, valid for physical drive only."
	::= {ePhysicalDeviceInformation 12}

a4ParityErrors OBJECT-TYPE
	SYNTAX		DmiInteger
	ACCESS		read-only
	STATUS		mandatory
	DESCRIPTION	"Number of Parity Errors, valid for physical drive only."
	::= {ePhysicalDeviceInformation 13}

a4MiscErrors OBJECT-TYPE
	SYNTAX		DmiCounter
	ACCESS		read-only
	STATUS		mandatory
	DESCRIPTION	"Number of Misc Errors, valid for physical drive only."
	::= {ePhysicalDeviceInformation 14}

a4ArrayList OBJECT-TYPE
	SYNTAX		DmiDisplaystring
	ACCESS		read-only
	STATUS		mandatory
	DESCRIPTION	"List Of Arrays of which this physical drive is part, if applicab
e."
	::= {ePhysicalDeviceInformation 15}

a4LogicalDriveList OBJECT-TYPE
	SYNTAX		DmiDisplaystring
	ACCESS		read-only
	STATUS		mandatory
	DESCRIPTION	"List of Logical Drives that depend on this physical drive,
if applicable."
	::= {ePhysicalDeviceInformation 16}

a4BusSpeed OBJECT-TYPE
	SYNTAX		DmiDisplaystring
	ACCESS		read-only
	STATUS		mandatory
	DESCRIPTION	"Bus Transfer Speed"
	::= {ePhysicalDeviceInformation 17}

a4BusWidth OBJECT-TYPE
	SYNTAX		DmiDisplaystring
	ACCESS		read-only
	STATUS		mandatory
	DESCRIPTION	"Bus Width"
	::= {ePhysicalDeviceInformation 18}

a4CommandQueuing OBJECT-TYPE
	SYNTAX		INTEGER {
		vFalse                                  	(0),
		vTrue                                   	(1)
	}
	ACCESS		read-only
	STATUS		mandatory
	DESCRIPTION	"Command Tagged Queuing Enabled"
	::= {ePhysicalDeviceInformation 19}

a4PfaErrors OBJECT-TYPE
	SYNTAX		DmiCounter
	ACCESS		read-only
	STATUS		mandatory
	DESCRIPTION	"SMART PFA Error Count, valid for physical drive only."
	::= {ePhysicalDeviceInformation 20}

SPhysicalDeviceInformation ::= SEQUENCE {
	a4ControllerNumber                      	DmiInteger,
	a4ChannelNumber                         	DmiInteger,
	a4TargetId                              	DmiInteger,
	a4Lun                                   	DmiInteger,
	a4OperationalState                      	DmiInteger,
	a4VendorId                              	DmiDisplaystring,
	a4ProductId                             	DmiDisplaystring,
	a4ProductRevisionLevel                  	DmiDisplaystring,
	a4SizeInMb                              	DmiInteger,
	a4DeviceType                            	DmiInteger,
	a4SoftErrors                            	DmiInteger,
	a4HardErrors                            	DmiCounter,
	a4ParityErrors                          	DmiInteger,
	a4MiscErrors                            	DmiCounter,
	a4ArrayList                             	DmiDisplaystring,
	a4LogicalDriveList                      	DmiDisplaystring,
	a4BusSpeed                              	DmiDisplaystring,
	a4BusWidth                              	DmiDisplaystring,
	a4CommandQueuing                        	DmiInteger,
	a4PfaErrors                             	DmiCounter
}



tMylexDacManagementSoftware OBJECT-TYPE
	SYNTAX		SEQUENCE OF SMylexDacManagementSoftware
	ACCESS		not-accessible
	STATUS		mandatory
	DESCRIPTION	"MDAC DAC Management Software Version Information."
	::= {dmtfGroups 5}

eMylexDacManagementSoftware OBJECT-TYPE
	SYNTAX		SMylexDacManagementSoftware
	ACCESS		not-accessible
	STATUS		mandatory
	DESCRIPTION	""
	INDEX		{a5ManagementSoftwareRevision}
	::= {tMylexDacManagementSoftware 1}

a5ManagementSoftwareRevision OBJECT-TYPE
	SYNTAX		DmiDisplaystring
	ACCESS		read-only
	STATUS		mandatory
	DESCRIPTION	"Mylex DAC Management Software Revision Information."
	::= {eMylexDacManagementSoftware 1}

a5ManagementSoftwareBuildDate OBJECT-TYPE
	SYNTAX		DmiDisplaystring
	ACCESS		read-only
	STATUS		mandatory
	DESCRIPTION	"Mylex DAC Management Software Build Date Information - month/dat
/year format."
	::= {eMylexDacManagementSoftware 2}

a5MylexDacDeviceDriverRevision OBJECT-TYPE
	SYNTAX		DmiDisplaystring
	ACCESS		read-only
	STATUS		mandatory
	DESCRIPTION	"Mylex DAC Device driver Revision Information."
	::= {eMylexDacManagementSoftware 3}

a5MylexDacDeviceDriverBuildDate OBJECT-TYPE
	SYNTAX		DmiDisplaystring
	ACCESS		read-only
	STATUS		mandatory
	DESCRIPTION	"Mylex DAC Device Driver Build Date Information - month/date/year
format."
	::= {eMylexDacManagementSoftware 4}

a5GamDriverRevision OBJECT-TYPE
	SYNTAX		DmiDisplaystring
	ACCESS		read-only
	STATUS		mandatory
	DESCRIPTION	"Mylex GAM Driver Revision Information."
	::= {eMylexDacManagementSoftware 5}

a5GamDriverBuildDate OBJECT-TYPE
	SYNTAX		DmiDisplaystring
	ACCESS		read-only
	STATUS		mandatory
	DESCRIPTION	"Mylex GAM Driver Build Date Information - date/month/year
format."
	::= {eMylexDacManagementSoftware 6}

SMylexDacManagementSoftware ::= SEQUENCE {
	a5ManagementSoftwareRevision            	DmiDisplaystring,
	a5ManagementSoftwareBuildDate           	DmiDisplaystring,
	a5MylexDacDeviceDriverRevision          	DmiDisplaystring,
	a5MylexDacDeviceDriverBuildDate         	DmiDisplaystring,
	a5GamDriverRevision                     	DmiDisplaystring,
	a5GamDriverBuildDate                    	DmiDisplaystring
}



tLogicalDriveStatistics OBJECT-TYPE
	SYNTAX		SEQUENCE OF SLogicalDriveStatistics
	ACCESS		not-accessible
	STATUS		mandatory
	DESCRIPTION	"Logical Drive Performance Statistics"
	::= {dmtfGroups 6}

eLogicalDriveStatistics OBJECT-TYPE
	SYNTAX		SLogicalDriveStatistics
	ACCESS		not-accessible
	STATUS		mandatory
	DESCRIPTION	""
	INDEX		{a6ControllerNumber, a6LogicalDriveNumber}
	::= {tLogicalDriveStatistics 1}

a6ControllerNumber OBJECT-TYPE
	SYNTAX		DmiInteger
	ACCESS		read-only
	STATUS		mandatory
	DESCRIPTION	"Controller Number - used as a key."
	::= {eLogicalDriveStatistics 1}

a6LogicalDriveNumber OBJECT-TYPE
	SYNTAX		DmiInteger
	ACCESS		read-only
	STATUS		mandatory
	DESCRIPTION	"Logical Drive Number - used as a key."
	::= {eLogicalDriveStatistics 2}

a6ReadRequests OBJECT-TYPE
	SYNTAX		DmiCounter
	ACCESS		read-only
	STATUS		mandatory
	DESCRIPTION	"Number of Read Requests."
	::= {eLogicalDriveStatistics 3}

a6DataReadInMb OBJECT-TYPE
	SYNTAX		DmiInteger
	ACCESS		read-only
	STATUS		mandatory
	DESCRIPTION	"Amount of Data Read from this logical drive - in MB."
	::= {eLogicalDriveStatistics 4}

a6WriteRequests OBJECT-TYPE
	SYNTAX		DmiCounter
	ACCESS		read-only
	STATUS		mandatory
	DESCRIPTION	"Number of Write Requests."
	::= {eLogicalDriveStatistics 5}

a6DataWrittenInMb OBJECT-TYPE
	SYNTAX		DmiInteger
	ACCESS		read-only
	STATUS		mandatory
	DESCRIPTION	"Amount of data written - in MB."
	::= {eLogicalDriveStatistics 6}

a6ReadCacheHitPercentage OBJECT-TYPE
	SYNTAX		DmiInteger
	ACCESS		read-only
	STATUS		mandatory
	DESCRIPTION	"Read Cache Hit Rate."
	::= {eLogicalDriveStatistics 7}

SLogicalDriveStatistics ::= SEQUENCE {
	a6ControllerNumber                      	DmiInteger,
	a6LogicalDriveNumber                    	DmiInteger,
	a6ReadRequests                          	DmiCounter,
	a6DataReadInMb                          	DmiInteger,
	a6WriteRequests                         	DmiCounter,
	a6DataWrittenInMb                       	DmiInteger,
	a6ReadCacheHitPercentage                	DmiInteger
}


tPhysicalDriveStatistics OBJECT-TYPE
	SYNTAX		SEQUENCE OF SPhysicalDriveStatistics
	ACCESS		not-accessible
	STATUS		mandatory
	DESCRIPTION	"Physical Drive Performance Statistics"
	::= {dmtfGroups 7}

ePhysicalDriveStatistics OBJECT-TYPE
	SYNTAX		SPhysicalDriveStatistics
	ACCESS		not-accessible
	STATUS		mandatory
	DESCRIPTION	""
	INDEX		{a7ControllerNumber, a7ChannelNumber, a7TargetId}
	::= {tPhysicalDriveStatistics 1}

a7ControllerNumber OBJECT-TYPE
	SYNTAX		DmiInteger
	ACCESS		read-only
	STATUS		mandatory
	DESCRIPTION	"Controller Number - used as a key."
	::= {ePhysicalDriveStatistics 1}

a7ChannelNumber OBJECT-TYPE
	SYNTAX		DmiInteger
	ACCESS		read-only
	STATUS		mandatory
	DESCRIPTION	"Channel Number - used as a key."
	::= {ePhysicalDriveStatistics 2}

a7TargetId OBJECT-TYPE
	SYNTAX		DmiInteger
	ACCESS		read-only
	STATUS		mandatory
	DESCRIPTION	"Physical Device Target Id - used as a key."
	::= {ePhysicalDriveStatistics 3}

a7Lun OBJECT-TYPE
	SYNTAX		DmiInteger
	ACCESS		read-only
	STATUS		mandatory
	DESCRIPTION	"LUN of the Physical Device."
	::= {ePhysicalDriveStatistics 4}

a7ReadRequests OBJECT-TYPE
	SYNTAX		DmiCounter
	ACCESS		read-only
	STATUS		mandatory
	DESCRIPTION	"Number of Read Requests."
	::= {ePhysicalDriveStatistics 5}

a7DataReadInMb OBJECT-TYPE
	SYNTAX		DmiInteger
	ACCESS		read-only
	STATUS		mandatory
	DESCRIPTION	"Amount of Data Read - in MB."
	::= {ePhysicalDriveStatistics 6}

a7WriteRequests OBJECT-TYPE
	SYNTAX		DmiCounter
	ACCESS		read-only
	STATUS		mandatory
	DESCRIPTION	"Number of Write Requests."
	::= {ePhysicalDriveStatistics 7}

a7DataWrittenInMb OBJECT-TYPE
	SYNTAX		DmiInteger
	ACCESS		read-only
	STATUS		mandatory
	DESCRIPTION	"Amount of data written - in MB."
	::= {ePhysicalDriveStatistics 8}

SPhysicalDriveStatistics ::= SEQUENCE {
	a7ControllerNumber                      	DmiInteger,
	a7ChannelNumber                         	DmiInteger,
	a7TargetId                              	DmiInteger,
	a7Lun                                   	DmiInteger,
	a7ReadRequests                          	DmiCounter,
	a7DataReadInMb                          	DmiInteger,
	a7WriteRequests                         	DmiCounter,
	a7DataWrittenInMb                       	DmiInteger
}


tFaultManagementCabinetInformation OBJECT-TYPE
	SYNTAX		SEQUENCE OF SFaultManagementCabinetInformation
	ACCESS		not-accessible
	STATUS		mandatory
	DESCRIPTION	"Fault Management Cabinet Information."
	::= {dmtfGroups 8}

eFaultManagementCabinetInformation OBJECT-TYPE
	SYNTAX		SFaultManagementCabinetInformation
	ACCESS		not-accessible
	STATUS		mandatory
	DESCRIPTION	""
	INDEX		{a8ControllerNumber, a8ChannelNumber, a8CabinetNumber}
	::= {tFaultManagementCabinetInformation 1}

a8ControllerNumber OBJECT-TYPE
	SYNTAX		DmiInteger
	ACCESS		read-only
	STATUS		mandatory
	DESCRIPTION	"Controller Number - used as a key."
	::= {eFaultManagementCabinetInformation 1}

a8ChannelNumber OBJECT-TYPE
	SYNTAX		DmiInteger
	ACCESS		read-only
	STATUS		mandatory
	DESCRIPTION	"Channel Number of the Channel to which the Cabinet is connected
- used as a key."
	::= {eFaultManagementCabinetInformation 2}

a8CabinetNumber OBJECT-TYPE
	SYNTAX		DmiInteger
	ACCESS		read-only
	STATUS		mandatory
	DESCRIPTION	"Cabinet Number - used as a key."
	::= {eFaultManagementCabinetInformation 3}

a8TargetId OBJECT-TYPE
	SYNTAX		DmiInteger
	ACCESS		read-only
	STATUS		mandatory
	DESCRIPTION	"Target Id of the Cabinet."
	::= {eFaultManagementCabinetInformation 4}

a8Lun OBJECT-TYPE
	SYNTAX		DmiInteger
	ACCESS		read-only
	STATUS		mandatory
	DESCRIPTION	"LUN of the Cabinet."
	::= {eFaultManagementCabinetInformation 5}

a8CabinetType OBJECT-TYPE
	SYNTAX		INTEGER {
		vConnerCr-6                             	(1),
		vConnerSmartCabinet                     	(2),
		vSafte1                                 	(3),
		vSafte                                  	(32),
		vSes                                    	(64),
		vUnknown                                	(255)
	}
	ACCESS		read-only
	STATUS		mandatory
	DESCRIPTION	"Fault Management Cabinet Type, such as Conner CR6, Conner
Smart and SAFTE etc."
	::= {eFaultManagementCabinetInformation 6}

a8NumberOfFans OBJECT-TYPE
	SYNTAX		DmiInteger
	ACCESS		read-only
	STATUS		mandatory
	DESCRIPTION	"Number of Fans in the cabinet."
	::= {eFaultManagementCabinetInformation 7}

a8NumberOfPowerSupplyUnits OBJECT-TYPE
	SYNTAX		DmiInteger
	ACCESS		read-only
	STATUS		mandatory
	DESCRIPTION	"Number of Power Supply Units in the cabinet."
	::= {eFaultManagementCabinetInformation 8}

a8NumberOfHeatSensors OBJECT-TYPE
	SYNTAX		DmiInteger
	ACCESS		read-only
	STATUS		mandatory
	DESCRIPTION	"Number of Heat Sensors in the cabinet."
	::= {eFaultManagementCabinetInformation 9}

a8NumberOfDriveSlots OBJECT-TYPE
	SYNTAX		DmiInteger
	ACCESS		read-only
	STATUS		mandatory
	DESCRIPTION	"Number of Drive Slots in the cabinet."
	::= {eFaultManagementCabinetInformation 10}

a8NumberOfDoorLocks OBJECT-TYPE
	SYNTAX		DmiInteger
	ACCESS		read-only
	STATUS		mandatory
	DESCRIPTION	"Number of Door Locks in the cabinet."
	::= {eFaultManagementCabinetInformation 11}

a8NumberOfSpeakers OBJECT-TYPE
	SYNTAX		DmiInteger
	ACCESS		read-only
	STATUS		mandatory
	DESCRIPTION	"Number of Speakers in the cabinet."
	::= {eFaultManagementCabinetInformation 12}

a8NumberOfFansCritical OBJECT-TYPE
	SYNTAX		DmiInteger
	ACCESS		read-only
	STATUS		mandatory
	DESCRIPTION	"Number of Fans in Critical State in the cabinet."
	::= {eFaultManagementCabinetInformation 13}

a8NumberOfPowerSupplyUnitsCritical OBJECT-TYPE
	SYNTAX		DmiInteger
	ACCESS		read-only
	STATUS		mandatory
	DESCRIPTION	"Number of Power Supply Units in Critical state in the cabinet."
	::= {eFaultManagementCabinetInformation 14}

a8NumberOfHeatSensorsCritical OBJECT-TYPE
	SYNTAX		DmiInteger
	ACCESS		read-only
	STATUS		mandatory
	DESCRIPTION	"Number of Heat Sensors in Critical state in the cabinet."
	::= {eFaultManagementCabinetInformation 15}

a8NumberOfFansFailed OBJECT-TYPE
	SYNTAX		DmiInteger
	ACCESS		read-only
	STATUS		mandatory
	DESCRIPTION	"Number of Fans in Failed State in the cabinet."
	::= {eFaultManagementCabinetInformation 16}

a8NumberOfPowerSupplyUnitsFailed OBJECT-TYPE
	SYNTAX		DmiInteger
	ACCESS		read-only
	STATUS		mandatory
	DESCRIPTION	"Number of Power Supply Units in Failed state in the cabinet."
	::= {eFaultManagementCabinetInformation 17}

a8NumberOfHeatSensorsFailed OBJECT-TYPE
	SYNTAX		DmiInteger
	ACCESS		read-only
	STATUS		mandatory
	DESCRIPTION	"Number of Heat Sensors in Failed state in the cabinet."
	::= {eFaultManagementCabinetInformation 18}

SFaultManagementCabinetInformation ::= SEQUENCE {
	a8ControllerNumber                      	DmiInteger,
	a8ChannelNumber                         	DmiInteger,
	a8CabinetNumber                         	DmiInteger,
	a8TargetId                              	DmiInteger,
	a8Lun                                   	DmiInteger,
	a8CabinetType                           	DmiInteger,
	a8NumberOfFans                          	DmiInteger,
	a8NumberOfPowerSupplyUnits              	DmiInteger,
	a8NumberOfHeatSensors                   	DmiInteger,
	a8NumberOfDriveSlots                    	DmiInteger,
	a8NumberOfDoorLocks                     	DmiInteger,
	a8NumberOfSpeakers                      	DmiInteger,
	a8NumberOfFansCritical                  	DmiInteger,
	a8NumberOfPowerSupplyUnitsCritical      	DmiInteger,
	a8NumberOfHeatSensorsCritical           	DmiInteger,
	a8NumberOfFansFailed                    	DmiInteger,
	a8NumberOfPowerSupplyUnitsFailed        	DmiInteger,
	a8NumberOfHeatSensorsFailed             	DmiInteger
}




tMylexRaidEventInformation OBJECT-TYPE
	SYNTAX		SEQUENCE OF SMylexRaidEventInformation
	ACCESS		not-accessible
	STATUS		mandatory
	DESCRIPTION	"Event Information for Mylex RAID events."
	::= {dmtfGroups 9}

eMylexRaidEventInformation OBJECT-TYPE
	SYNTAX		SMylexRaidEventInformation
	ACCESS		not-accessible
	STATUS		mandatory
	DESCRIPTION	""
	INDEX		{a9EventTableIndex}
	::= {tMylexRaidEventInformation 1}

a9EventTableIndex OBJECT-TYPE
	SYNTAX		DmiInteger
	ACCESS		read-only
	STATUS		mandatory
	DESCRIPTION	"Index to the event table, Used as a key. A total number of
256 events can be stored in the event table. However, the Event Table Index
can be greater than 256"
	::= {eMylexRaidEventInformation 1}

a9EventCode OBJECT-TYPE
	SYNTAX		INTEGER {
		vPhysdev-online                         	(1),
		vPhysdev-hotspare                       	(2),
		vPhysdev-hard-error                     	(3),
		vPhysdev-pfa                            	(4),
		vPhysdev-auto-rebuild-start             	(5),
		vPhysdev-manual-rebuild-start           	(6),
		vPhysdev-rebuild-done                   	(7),
		vPhysdev-rebuild-canceled               	(8),
		vPhysdev-rebuild-error                  	(9),
		vPhysdev-rebuild-newdev-failed          	(10),
		vPhysdev-rebuild-sysdev-failed          	(11),
		vPhysdev-dead                           	(12),
		vPhysdev-found                          	(13),
		vPhysdev-gone                           	(14),
		vPhysdev-unconfigured                   	(15),
		vPhysdev-expandcapacity-start           	(16),
		vPhysdev-expandcapacity-done            	(17),
		vPhysdev-expandcapacity-error           	(18),
		vPhysdev-command-timeout                	(19),
		vPhysdev-command-abort                  	(20),
		vPhysdev-command-retried                	(21),
		vPhysdev-parity-error                   	(22),
		vPhysdev-soft-error                     	(23),
		vPhysdev-misc-error                     	(24),
		vPhysdev-reset                          	(25),
		vPhysdev-activespare                    	(26),
		vPhysdev-warmspare                      	(27),
		vPhysdev-reqsense                       	(28),
		vPhysdev-init-started                   	(29),
		vPhysdev-init-done                      	(30),
		vPhysdev-init-failed                    	(31),
		vPhysdev-init-canceled                  	(32),
		vPhysdev-writerec-dead                  	(33),
		vPhysdev-reset-dead                     	(34),
		vPhysdev-dblcc-dead                     	(35),
		vPhysdev-removed-dead                   	(36),
		vPhysdev-grosserr-dead                  	(37),
		vPhysdev-badtag-dead                    	(38),
		vPhysdev-scsitmo-dead                   	(39),
		vPhysdev-sysreset-dead                  	(40),
		vPhysdev-bsypar-dead                    	(41),
		vPhysdev-bycmd-dead                     	(42),
		vPhysdev-seltmo-dead                    	(43),
		vPhysdev-seqerr-dead                    	(44),
		vPhysdev-unknownsts-dead                	(45),
		vPhysdev-notrdy-dead                    	(46),
		vPhysdev-missing-dead                   	(47),
		vPhysdev-codwrfail-dead                 	(48),
		vPhysdev-bdtwrfail-dead                 	(49),
		vPhysdev-offline                        	(50),
		vPhysdev-standby                        	(51),
		vPhysdev-rebuild                        	(52),
		vPhysdev-id-mismatch                    	(53),
		vPhysdev-failed-start                   	(54),
		vPhysdev-offset-set                     	(55),
		vPhysdev-set-bus-width                  	(56),
		vPhysdev-missing-onstartup              	(57),
		vPhysdev-rebuild-start-failed           	(58),
		vPhysdev-moving-to-other-chn            	(59),
		vPhysdev-offline-device-made-online     	(60),
		vPhysdev-standby-rebuild-start          	(61),
		vPhysdev-hot-spare-smaller              	(62),
		vPpilot-logical-disk-online             	(63),
		vPpilot-logical-disk-offline            	(64),
		vPpilot-logical-disk-path-failover      	(65),
		vPpilot-logical-disk-path-failback      	(66),
		vPhysdev-non-redundant-access           	(67),
		vPhysdev-type-invalid                   	(68),
		vPhysdev-soft-id                        	(69),
		vPhysdev-port-failed                    	(70),
		vCtldev-mirror-race-entry-failed        	(71),
		vCtldev-ctrl-params-checksum-failed     	(72),
		vFirmware-upgrade-started               	(73),
		vFirmware-upgrade-complete              	(74),
		vFirmware-upgrade-failed                	(75),
		vFibredev-loopid-softaddr-occurred      	(96),
		vPhysDev-clear-aborted						(97),
		vPhysdev-clear-failed						(98),
		vPhysdev-clear-started						(99),
		vPhysdev-clear-done							(100),
		vPhysdev-error								(101),
		vPhysdev-hs-smart-poll-failed				(102),
		vPhysdev-pr-corrected						(103),
		vPhysdev-reassign-write-failed				(104),
		vPhysdev-rebuild-medium-error				(105),
		vPhysdev-rec-correcting						(106),
		vPhysdev-recover-medium-error				(107),
		vPhysdev-redundant-path-broken				(108),
		vPhysdev-resundant-path-restored			(109),
		vPhysdev-dedicated-spare-no-longer-useful	(110),
		vPhysdev-spare-dedicated-created			(111),
		vPhysdev-spare-dedicated-disabled			(112),
		vPhysdev-spare-dedicated-not-useful-for-all	(113),
		vPhysdev-spare-global-created				(114),
		vPhysdev-spare-global-disabled				(115),
		vPhysdev-spare-global-not-covering-all		(116),
		vPhysdev-format-complete					(117),
		vPhysdev-format-started						(118),
		vPhysdev-too-small-for-autorebuild			(119),
		vPhysdev-bbm-log-80-percent-full			(120),
		vPhysdev-bbm-log-full						(121),
		vPhysdev-mediaerror-corrected           	(126),
		vMlxev-sysdev-check-done-with-error     	(127),
		vSysdev-check-start                     	(128),
		vSysdev-check-done                      	(129),
		vSysdev-check-canceled                  	(130),
		vSysdev-check-error                     	(131),
		vSysdev-check-sysdev-failed             	(132),
		vSysdev-check-physdev-failed            	(133),
		vSysdev-offline                         	(134),
		vSysdev-critical                        	(135),
		vSysdev-online                          	(136),
		vSysdev-auto-rebuild-start              	(137),
		vSysdev-manual-rebuild-start            	(138),
		vSysdev-rebuild-done                    	(139),
		vSysdev-rebuild-canceled                	(140),
		vSysdev-rebuild-error                   	(141),
		vSysdev-rebuild-newdev-failed           	(142),
		vSysdev-rebuild-sysdev-failed           	(143),
		vSysdev-init-started                    	(144),
		vSysdev-init-done                       	(145),
		vSysdev-init-canceled                   	(146),
		vSysdev-init-failed                     	(147),
		vSysdev-found                           	(148),
		vSysdev-gone                            	(149),
		vSysdev-expandcapacity-start            	(150),
		vSysdev-expandcapacity-done             	(151),
		vSysdev-expandcapacity-error            	(152),
		vSysdev-badblock                        	(153),
		vSysdev-sizechanged                     	(154),
		vSysdev-typechanged                     	(155),
		vSysdev-baddatablock                    	(156),
		vSysdev-wr-lun-map                      	(157),
		vSysdev-dataread-from-block-in-bdt      	(158),
		vSysdev-data-for-block-lost             	(159),
		vSysdev-offline-device-made-available-wi	(160),
		vSysdev-offline-device-made-available   	(161),
		vSysdev-standby-rebuild-start           	(162),
		vSysdev-expandcapacity-medium-error			(163),
		vSysdev-expandcapacity-resume				(164),
		vSysdev-expandcapacity-resume-failed		(165),
		vSysdev-properties-changed					(166),
		vSysdev-inconsistent-due-at-startup			(167),
		vSysdev-bg-init-started                 	(176),
		vSysdev-bg-init-stopped                 	(177),
		vSysdev-bg-init-paused                  	(178),
		vSysdev-bg-init-restarted               	(179),
		vSysdev-bg-init-failed                  	(180),
		vSysdev-bg-init-completed               	(181),
		vSysdev-data-loss-low-bbu-charge        	(182),
		vSysdev-check-cons-mismatch             	(183),
		vMlxev-sysdev-cluster-change            	(184),
		vFmtfan-failed                          	(256),
		vFmtfan-ok                              	(257),
		vAemi-fan-failed                        	(258),
		vFmtfan-notpresent                      	(259),
		vFmtpower-failed                        	(272),
		vFmtpower-ok                            	(273),
		vAemi-pwr-supply-failed                 	(274),
		vFmtpower-notpresent                    	(275),
		vFmtheat-bad                            	(288),
		vFmtheat-critical                       	(289),
		vFmtheat-ok                             	(290),
		vAemi-over-temperature                  	(291),
		vFmtheat-notpresent                     	(292),
		vFmtstwk-failed                         	(304),
		vFmtstwk-critical                       	(305),
		vFmtstwk-ok                             	(306),
		vFmt-ups-disabled                       	(307),
		vFmt-ups-ac-fail                        	(308),
		vFmt-ups-bat-low                        	(309),
		vFmt-ups-failed                         	(310),
		vFmt-ups-ok                             	(311),
		vEnclfan-failed                         	(320),
		vEnclfan-ok                             	(321),
		vEnclfan-notpresent                     	(322),
		vEnclpower-failed                       	(323),
		vEnclpower-ok                           	(324),
		vEnclpower-notpresent                   	(325),
		vEnclheat-bad                           	(326),
		vEnclheat-critical                      	(327),
		vEnclheat-ok                            	(328),
		vEnclheat-notpresent                    	(329),
		vEnclaccess-critical                    	(330),
		vEnclaccess-ok                          	(331),
		vEnclaccess-offline                     	(332),
		vEnclses-softaddr-occurred              	(333),
		vEnclaccess-ready                       	(334),
		vEnclheat-unknown                       	(335),
		vEnclpower-unknown                      	(336),
		vEnclfan-unknown                        	(337),
		vEnclosure-shutdown                     	(338),
		vEnclcold-warn                          	(339),
		vEnclcold-fail                          	(340),
		vEnclses-discovered							(341),
		vEnclsafte-discovered						(342),
		vEnclsim-failed								(343),
		vEnclsim-ok									(344),
		vEnclsim-notpresent							(345),
		vEnclmax-per-port-exceed					(346),
		vEnclfirmware-mismatch						(347),
		vEnclsensor-bad								(348),
		vEnclphy-bad								(349),
		vEncl-sas-sata-mixing-detected   			(350),
		vEncl-ses-hotplug-detected					(351),
		vEncl-power-supply-off						(352),
		vEncl-power-supply-on						(353),
		vEncl-power-supply-cable-removed			(355),
		vEncl-fan-returned-to-normal				(356),
		vEncl-temp-differential						(357),
		vSystem-started                         	(384),
		vCtldev-writeback-error                 	(385),
		vCtldev-state-table-full                	(386),
		vCtldev-dead                            	(388),
		vCtldev-reset                           	(389),
		vCtldev-found                           	(390),
		vCtldev-gone                            	(391),
		vCtldev-bbu-found                       	(392),
		vCtldev-bbu-power-low                   	(393),
		vCtldev-bbu-power-ok                    	(394),
		vCtldev-power-off                       	(395),
		vCtldev-power-on                        	(396),
		vCtldev-online                          	(397),
		vCtldev-offline                         	(398),
		vCtldev-critical                        	(399),
		vCtldev-bbu-recond-start                	(400),
		vCtldev-bbu-recond-done                 	(401),
		vCtldev-bbu-recond-abort                	(402),
		vCtldev-installation-aborted            	(403),
		vCtldev-firmware-mismatch               	(404),
		vCtldev-bbu-noresponse                  	(405),
		vCtldev-warm-boot-error                 	(406),
		vCtldev-bbu-calibrate-start             	(407),
		vCtldev-bbu-calibrate-done              	(408),
		vCtldev-bbu-calibrate-abort             	(409),
		vCtldev-bbu-no-battery                  	(410),
		vCtldev-conserv-cache-mode              	(411),
		vCtldev-normal-cache-mode               	(412),
		vCtldev-dev-start-cmplt                 	(413),
		vCtldev-soft-ecc-corrected              	(414),
		vCtldev-hard-ecc-corrected              	(415),
		vCtldev-bbu-recond-needed               	(416),
		vCtldev-removed-ptnr                    	(417),
		vCtldev-bbu-out-of-service              	(418),
		vCtldev-update-ptnr-status              	(419),
		vCtldev-relinquish-ptnr                 	(420),
		vCtldev-inserted-ptnr                   	(421),
		vCtldev-dual-enabled                    	(422),
		vCtldev-kill-ptnr                       	(423),
		vCtldev-nexus                           	(424),
		vCtldev-bad-bootrom-image               	(425),
		vCtldev-bad-mac-address                 	(426),
		vCtldev-mirror-race-recovery-failed     	(427),
		vCtldev-mirror-critical-drive           	(428),
		vCtldev-in-cluster                      	(429),
		vCtldev-not-in-cluster                  	(430),
		vSysdev-data-loss-improper-shutdown     	(431),
		vCtldev-automatic-flash-started         	(432),
		vCtldev-negotiation-failed-jumpers      	(433),
		vCtldev-negotiation-same-id             	(434),
		vCtldev-negotiation-board-type          	(435),
		vCtldev-negotiation-disk-channels       	(436),
		vCtldev-negotiation-host-channels       	(437),
		vCtldev-negotiation-memory-size         	(438),
		vCtldev-negotiation-cache-size          	(439),
		vCtldev-mirror-race-table-error         	(440),
		vCtldev-stop-rejected                   	(441),
		vCtldev-patrolread-iteration-done       	(442),
		vCtldev-writeback-to-writethru          	(443),
		vCtldev-writethru-to-writeback          	(444),
		vCtldev-update-from-peer                	(445),
		vCtldev-cache-flushed                   	(446),
		vCtldev-cache-not-flushed               	(447),
		vCtldev-cc-rate-changed						(448),
		vCtldev-bgi-rate-changed					(449),
		vCtldev-flush-rate-changed					(450),
		vCtldev-pr-rate-changed						(451),
		vCtldev-rbld-rate-changed					(452),
		vCtldev-recon-rate-changed					(453),
		vCtldev-cluster-down						(454),
		vCtldev-alarm-disabled						(455),
		vCtldev-alarm-enabled						(456),
		vCtldev-cache-reboot-cant-recover			(457),
		vCtldevcache-reboot-recover					(458),
		vCtldev-cache-version-mismatch				(459),
		vCtldev-factory-defaults					(460),
		vCtldev-hibernate							(461),
		vCtldev-log-cleared							(462),
		vCtldev-log-wrapped							(463),
		vCtldev-not-enough-memory					(464),
		vCtldev-pr-pause							(465),
		vCtldev-pr-resume							(466),
		vCtldev-pr-start							(467),
		vCtldev-shutdown							(468),
		vCtldev-user-entered-debugger				(469),
		vCtldev-bbu-temp-high						(470),
		vCtldev-bbu-charging						(471),
		vCtldev-bbu-discharging						(472),
		vCtldev-replacement-needed					(473),
		vCtldev-relearn-timeout						(474),
		vCtldev-relearn-pending						(475),
		vCtldev-battery-cap-below-soh-threshold		(476),
		vCtldev-battery-cap-above-soh-threshold		(477),
		vCtldev-battery-good						(478),
		vCtldev-battery-bad							(479),
		vCtldev-Bbu-Charge-Complete					(480),
		vCtldev-Bbu-recond-requested				(481),
		vCtldev-cache-discard-by-user				(482),
		vCtldev-boot-config-missing					(483),
		vSystem-started-new                     	(512),
		vSystem-size-table-full                 	(513),
		vSystem-user-logged-in                  	(514),
		vSystem-user-logged-out                 	(515),
		vSystem-alive                           	(516),
		vSystem-dead                            	(517),
		vAutoboot-changed                       	(518),
		vCtldev-bbu-batt-test-start             	(519),
		vCtldev-bbu-batt-test-complete          	(520),
		vCtldev-bbu-batt-test-canceled          	(521),
		vCtldev-bbu-batt-test-failed            	(522),
		vChannel-failed                         	(640),
		vChannel-ok                             	(641),
		vChannel-scsi-bus-dead                  	(642),
		vChannel-scsi-bus-alive                 	(643),
		vChannel-fiber-dead                     	(644),
		vChannel-fiber-alive                    	(645),
		vLog-empty                              	(700),
		vLog-out-sync                           	(701),
		vLog-request-sense                      	(702),
		vLog-set-rtc                            	(703),
		vCfg-new                                	(800),
		vCfg-clear                              	(801),
		vCfg-invalid                            	(802),
		vCfg-cod-access-error                   	(803),
		vCfg-cod-converted                      	(804),
		vCfg-cod-import-failed                  	(805),
		vDebug-dump-generated                   	(806),
		vDebug-dump-generated-partner           	(807),
		vCfg-cod-not-found                      	(808),
		vCfg-cod-lun-map-not-found              	(809),
		vFirmware-boot								(810),
		vfirmware-cache-config-mismatch				(811),
		vFirmware-cache-processed					(812),
		vSas-Topology-loop-detection				(960),
		vSas-Topology-unaddressable-device			(961),
		vSas-Topology-multiple-ports-to-same-addr	(962),
		vSas-Topology-expander-error				(963),
		vSas-Topology-smp-timeout					(964),
		vSas-Topology-out-of-route-entries			(965),
		vSas-Topology-index-not-found				(966),
		vSas-Topology-smp-function-failed			(967),
		vSas-Topology-smp-crc-error					(968),
		vSas-Topology-multiple-subtractive			(969),
		vSas-Topology-table-to-table				(970),
		vSas-Topology-multiple-paths				(971),
		vUnknown                                	(268435455)
	}
	ACCESS		read-only
	STATUS		mandatory
	DESCRIPTION	"Mylex RAID event code."
	::= {eMylexRaidEventInformation 2}

a9EventTimeStamp OBJECT-TYPE
	SYNTAX		DmiInteger
	ACCESS		read-only
	STATUS		mandatory
	DESCRIPTION	"Time Stamp associated with this event. It's the number of
seconds since midnight(00:00:00) January 1, 1970 GMT."
	::= {eMylexRaidEventInformation 3}

a9ControllerNumber OBJECT-TYPE
	SYNTAX		DmiInteger
	ACCESS		read-only
	STATUS		mandatory
	DESCRIPTION	"Controller Number of the controller, which causes the event,
if applicable"
	::= {eMylexRaidEventInformation 4}

a9ChannelNumber OBJECT-TYPE
	SYNTAX		DmiInteger
	ACCESS		read-only
	STATUS		mandatory
	DESCRIPTION	"Channel Number of the device, which causes the event, if
applicable"
	::= {eMylexRaidEventInformation 5}

a9TargetNumber OBJECT-TYPE
	SYNTAX		DmiInteger
	ACCESS		read-only
	STATUS		mandatory
	DESCRIPTION	"Target Id of the physical device, which causes the event,
if applicable"
	::= {eMylexRaidEventInformation 6}

a9Lun OBJECT-TYPE
	SYNTAX		DmiInteger
	ACCESS		read-only
	STATUS		mandatory
	DESCRIPTION	"LUN of the device, which causes the event, if applicable"
	::= {eMylexRaidEventInformation 7}

a9LogicalDriveNumber OBJECT-TYPE
	SYNTAX		DmiInteger
	ACCESS		read-only
	STATUS		mandatory
	DESCRIPTION	"Drive Number of the Logical Drive, which causes the event,
if applicable"
	::= {eMylexRaidEventInformation 8}

a9FmtCabinetNumber OBJECT-TYPE
	SYNTAX		DmiInteger
	ACCESS		read-only
	STATUS		mandatory
	DESCRIPTION	"Fault Management Cabinet Number of the cabinet, which causes
the event, if applicable"
	::= {eMylexRaidEventInformation 9}

a9FanUnitNumber OBJECT-TYPE
	SYNTAX		DmiInteger
	ACCESS		read-only
	STATUS		mandatory
	DESCRIPTION	"Unit Number of the fan which, causes the event, if applicable"
	::= {eMylexRaidEventInformation 10}

a9PowerSupplyUnitNumber OBJECT-TYPE
	SYNTAX		DmiInteger
	ACCESS		read-only
	STATUS		mandatory
	DESCRIPTION	"Unit Nubmer of the PSU which, causes the event, if applicable"
	::= {eMylexRaidEventInformation 11}

a9HeatSensorUnitNumber OBJECT-TYPE
	SYNTAX		DmiInteger
	ACCESS		read-only
	STATUS		mandatory
	DESCRIPTION	"Unit Number of the Heat Sensor, which causes the event, if
applicable"
	::= {eMylexRaidEventInformation 12}

a9EnclosureUnitNumber OBJECT-TYPE
	SYNTAX		DmiInteger
	ACCESS		read-only
	STATUS		mandatory
	DESCRIPTION	"Unit Number of the Enclosure Unit, which causes the event,
if applicable"
	::= {eMylexRaidEventInformation 13}

SMylexRaidEventInformation ::= SEQUENCE {
	a9EventTableIndex                       	DmiInteger,
	a9EventCode                             	DmiInteger,
	a9EventTimeStamp                        	DmiInteger,
	a9ControllerNumber                      	DmiInteger,
	a9ChannelNumber                         	DmiInteger,
	a9TargetNumber                          	DmiInteger,
	a9Lun                                   	DmiInteger,
	a9LogicalDriveNumber                    	DmiInteger,
	a9FmtCabinetNumber                      	DmiInteger,
	a9FanUnitNumber                         	DmiInteger,
	a9PowerSupplyUnitNumber                 	DmiInteger,
	a9HeatSensorUnitNumber                  	DmiInteger,
	a9EnclosureUnitNumber                   	DmiInteger
}



tBatteryBackupUnitInformation OBJECT-TYPE
	SYNTAX		SEQUENCE OF SBatteryBackupUnitInformation
	ACCESS		not-accessible
	STATUS		mandatory
	DESCRIPTION	"This group provides Battery Backup Unit Information."
	::= {dmtfGroups 10}

eBatteryBackupUnitInformation OBJECT-TYPE
	SYNTAX		SBatteryBackupUnitInformation
	ACCESS		not-accessible
	STATUS		mandatory
	DESCRIPTION	""
	INDEX		{a10ControllerNumber}
	::= {tBatteryBackupUnitInformation 1}

a10ControllerNumber OBJECT-TYPE
	SYNTAX		DmiInteger
	ACCESS		read-only
	STATUS		mandatory
	DESCRIPTION	"Controller Number of the controller to which this BBU is
connected."
	::= {eBatteryBackupUnitInformation 1}

a10OperationalState OBJECT-TYPE
	SYNTAX		DmiInteger
	ACCESS		read-only
	STATUS		mandatory
	DESCRIPTION	"Operational state of Battery Backup Unit."
	::= {eBatteryBackupUnitInformation 2}

a10BatteryType OBJECT-TYPE
	SYNTAX		INTEGER {
		vUnknown                                	(0),
		vNickelCadmium                          	(1),
		vNimh                                   	(2),
		vLithiumion                             	(3),
		vNoBatterBackupPresent                  	(254)
	}
	ACCESS		read-only
	STATUS		mandatory
	DESCRIPTION	"Battery Type."
	::= {eBatteryBackupUnitInformation 3}

a10CurrentPowerInHours OBJECT-TYPE
	SYNTAX		DmiInteger
	ACCESS		read-only
	STATUS		mandatory
	DESCRIPTION	"Current Power in Hours."
	::= {eBatteryBackupUnitInformation 4}

a10MaximumPowerInHours OBJECT-TYPE
	SYNTAX		DmiInteger
	ACCESS		read-only
	STATUS		mandatory
	DESCRIPTION	"Maximum Power in Hours."
	::= {eBatteryBackupUnitInformation 5}

a10ThresholdValueInHours OBJECT-TYPE
	SYNTAX		DmiInteger
	ACCESS		read-only
	STATUS		mandatory
	DESCRIPTION	"Threshold Value in Hours."
	::= {eBatteryBackupUnitInformation 6}

a10ChargeLevelInPercentage OBJECT-TYPE
	SYNTAX		DmiInteger
	ACCESS		read-only
	STATUS		mandatory
	DESCRIPTION	"Battery Charge Level (in percentage)."
	::= {eBatteryBackupUnitInformation 7}

a10Version OBJECT-TYPE
	SYNTAX		DmiInteger
	ACCESS		read-only
	STATUS		mandatory
	DESCRIPTION	"BBU Hardware Version Number."
	::= {eBatteryBackupUnitInformation 8}

a10OperationalStateString OBJECT-TYPE
	SYNTAX		DmiDisplaystring
	ACCESS		read-only
	STATUS		mandatory
	DESCRIPTION	"BBU Operational State String."
	::= {eBatteryBackupUnitInformation 9}

SBatteryBackupUnitInformation ::= SEQUENCE {
	a10ControllerNumber                     	DmiInteger,
	a10OperationalState                     	DmiInteger,
	a10BatteryType                          	DmiInteger,
	a10CurrentPowerInHours                  	DmiInteger,
	a10MaximumPowerInHours                  	DmiInteger,
	a10ThresholdValueInHours                	DmiInteger,
	a10ChargeLevelInPercentage              	DmiInteger,
	a10Version                              	DmiInteger,
	a10OperationalStateString               	DmiDisplaystring
}
-- The trap partion of the mib file is generated by events2mib.exe
-- Input is from the events.dat file which describes events for firmware 7.x


physdevOnline    TRAP-TYPE
    ENTERPRISE  eMylexRaidEventInformation
    VARIABLES   {
	a9EventCode,
	a9ControllerNumber,
	a9ChannelNumber,
	a9TargetNumber,
	a9EventTimeStamp
    }
          DESCRIPTION
           "A physical disk has been placed online."
           --#SUMMARY  "[ctl: %d chn: %d tgt: %d :] A physical disk has been placed online." 
           --#ARGUMENTS {1,2,3}
           --#SEVERITY INFORMATIONAL
           --#TIMEINDEX 4
           --#STATE OPERATIONAL
           ::= 1

physdevHotspare    TRAP-TYPE
    ENTERPRISE  eMylexRaidEventInformation
    VARIABLES   {
	a9EventCode,
	a9ControllerNumber,
	a9ChannelNumber,
	a9TargetNumber,
	a9EventTimeStamp
    }
          DESCRIPTION
           "A physical disk has been added as hot spare."
           --#SUMMARY  "[ctl: %d chn: %d tgt: %d :] A physical disk has been added as hot spare." 
           --#ARGUMENTS {1,2,3}
           --#SEVERITY INFORMATIONAL
           --#TIMEINDEX 4
           --#STATE OPERATIONAL
           ::= 2

physdevHardError    TRAP-TYPE
    ENTERPRISE  eMylexRaidEventInformation
    VARIABLES   {
	a9EventCode,
	a9ControllerNumber,
	a9ChannelNumber,
	a9TargetNumber,
	a9EventTimeStamp
    }
          DESCRIPTION
           "Physical disk error found."
           --#SUMMARY  "[ctl: %d chn: %d tgt: %d :] Physical disk error found." 
           --#ARGUMENTS {1,2,3}
           --#SEVERITY MAJOR
           --#TIMEINDEX 4
           --#STATE DEGRADED
           ::= 3

physdevPfa    TRAP-TYPE
    ENTERPRISE  eMylexRaidEventInformation
    VARIABLES   {
	a9EventCode,
	a9ControllerNumber,
	a9ChannelNumber,
	a9TargetNumber,
	a9EventTimeStamp
    }
          DESCRIPTION
           "Physical disk PFA condition found; this disk may fail soon."
           --#SUMMARY  "[ctl: %d chn: %d tgt: %d :] Physical disk PFA condition found; this disk may fail soon." 
           --#ARGUMENTS {1,2,3}
           --#SEVERITY MAJOR
           --#TIMEINDEX 4
           --#STATE DEGRADED
           ::= 4

physdevAutoRebuildStart    TRAP-TYPE
    ENTERPRISE  eMylexRaidEventInformation
    VARIABLES   {
	a9EventCode,
	a9ControllerNumber,
	a9ChannelNumber,
	a9TargetNumber,
	a9EventTimeStamp
    }
          DESCRIPTION
           "An automatic rebuild has started."
           --#SUMMARY  "[ctl: %d chn: %d tgt: %d :] An automatic rebuild has started." 
           --#ARGUMENTS {1,2,3}
           --#SEVERITY INFORMATIONAL
           --#TIMEINDEX 4
           --#STATE OPERATIONAL
           ::= 5

physdevManualRebuildStart    TRAP-TYPE
    ENTERPRISE  eMylexRaidEventInformation
    VARIABLES   {
	a9EventCode,
	a9ControllerNumber,
	a9ChannelNumber,
	a9TargetNumber,
	a9EventTimeStamp
    }
          DESCRIPTION
           "A rebuild has started."
           --#SUMMARY  "[ctl: %d chn: %d tgt: %d :] A rebuild has started." 
           --#ARGUMENTS {1,2,3}
           --#SEVERITY INFORMATIONAL
           --#TIMEINDEX 4
           --#STATE OPERATIONAL
           ::= 6

physdevRebuildDone    TRAP-TYPE
    ENTERPRISE  eMylexRaidEventInformation
    VARIABLES   {
	a9EventCode,
	a9ControllerNumber,
	a9ChannelNumber,
	a9TargetNumber,
	a9EventTimeStamp
    }
          DESCRIPTION
           "Rebuild is over."
           --#SUMMARY  "[ctl: %d chn: %d tgt: %d :] Rebuild is over." 
           --#ARGUMENTS {1,2,3}
           --#SEVERITY INFORMATIONAL
           --#TIMEINDEX 4
           --#STATE OPERATIONAL
           ::= 7

physdevRebuildCanceled    TRAP-TYPE
    ENTERPRISE  eMylexRaidEventInformation
    VARIABLES   {
	a9EventCode,
	a9ControllerNumber,
	a9ChannelNumber,
	a9TargetNumber,
	a9EventTimeStamp
    }
          DESCRIPTION
           "Rebuild is cancelled."
           --#SUMMARY  "[ctl: %d chn: %d tgt: %d :] Rebuild is cancelled." 
           --#ARGUMENTS {1,2,3}
           --#SEVERITY INFORMATIONAL
           --#TIMEINDEX 4
           --#STATE OPERATIONAL
           ::= 8

physdevRebuildError    TRAP-TYPE
    ENTERPRISE  eMylexRaidEventInformation
    VARIABLES   {
	a9EventCode,
	a9ControllerNumber,
	a9ChannelNumber,
	a9TargetNumber,
	a9EventTimeStamp
    }
          DESCRIPTION
           "Rebuild stopped with error."
           --#SUMMARY  "[ctl: %d chn: %d tgt: %d :] Rebuild stopped with error." 
           --#ARGUMENTS {1,2,3}
           --#SEVERITY MAJOR
           --#TIMEINDEX 4
           --#STATE DEGRADED
           ::= 9

physdevRebuildNewdevFailed    TRAP-TYPE
    ENTERPRISE  eMylexRaidEventInformation
    VARIABLES   {
	a9EventCode,
	a9ControllerNumber,
	a9ChannelNumber,
	a9TargetNumber,
	a9EventTimeStamp
    }
          DESCRIPTION
           "Rebuild stopped with error. New physical disk failed."
           --#SUMMARY  "[ctl: %d chn: %d tgt: %d :] Rebuild stopped with error. New physical disk failed." 
           --#ARGUMENTS {1,2,3}
           --#SEVERITY MAJOR
           --#TIMEINDEX 4
           --#STATE DEGRADED
           ::= 10

physdevRebuildSysdevFailed    TRAP-TYPE
    ENTERPRISE  eMylexRaidEventInformation
    VARIABLES   {
	a9EventCode,
	a9ControllerNumber,
	a9ChannelNumber,
	a9TargetNumber,
	a9EventTimeStamp
    }
          DESCRIPTION
           "Rebuild stopped because logical drive failed."
           --#SUMMARY  "[ctl: %d chn: %d tgt: %d :] Rebuild stopped because logical drive failed." 
           --#ARGUMENTS {1,2,3}
           --#SEVERITY MAJOR
           --#TIMEINDEX 4
           --#STATE DEGRADED
           ::= 11

physdevDead    TRAP-TYPE
    ENTERPRISE  eMylexRaidEventInformation
    VARIABLES   {
	a9EventCode,
	a9ControllerNumber,
	a9ChannelNumber,
	a9TargetNumber,
	a9EventTimeStamp
    }
          DESCRIPTION
           "A physical disk has failed."
           --#SUMMARY  "[ctl: %d chn: %d tgt: %d :] A physical disk has failed." 
           --#ARGUMENTS {1,2,3}
           --#SEVERITY MAJOR
           --#TIMEINDEX 4
           --#STATE DEGRADED
           ::= 12

physdevFound    TRAP-TYPE
    ENTERPRISE  eMylexRaidEventInformation
    VARIABLES   {
	a9EventCode,
	a9ControllerNumber,
	a9ChannelNumber,
	a9TargetNumber,
	a9EventTimeStamp
    }
          DESCRIPTION
           "A new physical disk has been found."
           --#SUMMARY  "[ctl: %d chn: %d tgt: %d :] A new physical disk has been found." 
           --#ARGUMENTS {1,2,3}
           --#SEVERITY INFORMATIONAL
           --#TIMEINDEX 4
           --#STATE OPERATIONAL
           ::= 13

physdevGone    TRAP-TYPE
    ENTERPRISE  eMylexRaidEventInformation
    VARIABLES   {
	a9EventCode,
	a9ControllerNumber,
	a9ChannelNumber,
	a9TargetNumber,
	a9EventTimeStamp
    }
          DESCRIPTION
           "A physical disk has been removed."
           --#SUMMARY  "[ctl: %d chn: %d tgt: %d :] A physical disk has been removed." 
           --#ARGUMENTS {1,2,3}
           --#SEVERITY INFORMATIONAL
           --#TIMEINDEX 4
           --#STATE OPERATIONAL
           ::= 14

physdevUnconfigured    TRAP-TYPE
    ENTERPRISE  eMylexRaidEventInformation
    VARIABLES   {
	a9EventCode,
	a9ControllerNumber,
	a9ChannelNumber,
	a9TargetNumber,
	a9EventTimeStamp
    }
          DESCRIPTION
           "A previously configured physical disk is now available."
           --#SUMMARY  "[ctl: %d chn: %d tgt: %d :] A previously configured physical disk is now available." 
           --#ARGUMENTS {1,2,3}
           --#SEVERITY INFORMATIONAL
           --#TIMEINDEX 4
           --#STATE OPERATIONAL
           ::= 15

physdevExpandcapacityStart    TRAP-TYPE
    ENTERPRISE  eMylexRaidEventInformation
    VARIABLES   {
	a9EventCode,
	a9ControllerNumber,
	a9ChannelNumber,
	a9TargetNumber,
	a9EventTimeStamp
    }
          DESCRIPTION
           "Expand Capacity Started."
           --#SUMMARY  "[ctl: %d chn: %d tgt: %d :] Expand Capacity Started." 
           --#ARGUMENTS {1,2,3}
           --#SEVERITY INFORMATIONAL
           --#TIMEINDEX 4
           --#STATE OPERATIONAL
           ::= 16

physdevExpandcapacityDone    TRAP-TYPE
    ENTERPRISE  eMylexRaidEventInformation
    VARIABLES   {
	a9EventCode,
	a9ControllerNumber,
	a9ChannelNumber,
	a9TargetNumber,
	a9EventTimeStamp
    }
          DESCRIPTION
           "Expand Capacity Completed."
           --#SUMMARY  "[ctl: %d chn: %d tgt: %d :] Expand Capacity Completed." 
           --#ARGUMENTS {1,2,3}
           --#SEVERITY INFORMATIONAL
           --#TIMEINDEX 4
           --#STATE OPERATIONAL
           ::= 17

physdevExpandcapacityError    TRAP-TYPE
    ENTERPRISE  eMylexRaidEventInformation
    VARIABLES   {
	a9EventCode,
	a9ControllerNumber,
	a9ChannelNumber,
	a9TargetNumber,
	a9EventTimeStamp
    }
          DESCRIPTION
           "Expand Capacity Stopped with error."
           --#SUMMARY  "[ctl: %d chn: %d tgt: %d :] Expand Capacity Stopped with error." 
           --#ARGUMENTS {1,2,3}
           --#SEVERITY MAJOR
           --#TIMEINDEX 4
           --#STATE DEGRADED
           ::= 18

physdevCommandTimeout    TRAP-TYPE
    ENTERPRISE  eMylexRaidEventInformation
    VARIABLES   {
	a9EventCode,
	a9ControllerNumber,
	a9ChannelNumber,
	a9TargetNumber,
	a9EventTimeStamp
    }
          DESCRIPTION
           "SCSI command timeout on physical device."
           --#SUMMARY  "[ctl: %d chn: %d tgt: %d :] SCSI command timeout on physical device." 
           --#ARGUMENTS {1,2,3}
           --#SEVERITY MAJOR
           --#TIMEINDEX 4
           --#STATE DEGRADED
           ::= 19

physdevCommandAbort    TRAP-TYPE
    ENTERPRISE  eMylexRaidEventInformation
    VARIABLES   {
	a9EventCode,
	a9ControllerNumber,
	a9ChannelNumber,
	a9TargetNumber,
	a9EventTimeStamp
    }
          DESCRIPTION
           "SCSI command abort on physical disk."
           --#SUMMARY  "[ctl: %d chn: %d tgt: %d :] SCSI command abort on physical disk." 
           --#ARGUMENTS {1,2,3}
           --#SEVERITY CRITICAL
           --#TIMEINDEX 4
           --#STATE NONOPERATIONAL
           ::= 20

physdevCommandRetried    TRAP-TYPE
    ENTERPRISE  eMylexRaidEventInformation
    VARIABLES   {
	a9EventCode,
	a9ControllerNumber,
	a9ChannelNumber,
	a9TargetNumber,
	a9EventTimeStamp
    }
          DESCRIPTION
           "SCSI command retried on physical disk."
           --#SUMMARY  "[ctl: %d chn: %d tgt: %d :] SCSI command retried on physical disk." 
           --#ARGUMENTS {1,2,3}
           --#SEVERITY MINOR
           --#TIMEINDEX 4
           --#STATE OPERATIONAL
           ::= 21

physdevParityError    TRAP-TYPE
    ENTERPRISE  eMylexRaidEventInformation
    VARIABLES   {
	a9EventCode,
	a9ControllerNumber,
	a9ChannelNumber,
	a9TargetNumber,
	a9EventTimeStamp
    }
          DESCRIPTION
           "Parity error found."
           --#SUMMARY  "[ctl: %d chn: %d tgt: %d :] Parity error found." 
           --#ARGUMENTS {1,2,3}
           --#SEVERITY MAJOR
           --#TIMEINDEX 4
           --#STATE DEGRADED
           ::= 22

physdevSoftError    TRAP-TYPE
    ENTERPRISE  eMylexRaidEventInformation
    VARIABLES   {
	a9EventCode,
	a9ControllerNumber,
	a9ChannelNumber,
	a9TargetNumber,
	a9EventTimeStamp
    }
          DESCRIPTION
           "Soft error found."
           --#SUMMARY  "[ctl: %d chn: %d tgt: %d :] Soft error found." 
           --#ARGUMENTS {1,2,3}
           --#SEVERITY MINOR
           --#TIMEINDEX 4
           --#STATE OPERATIONAL
           ::= 23

physdevMiscError    TRAP-TYPE
    ENTERPRISE  eMylexRaidEventInformation
    VARIABLES   {
	a9EventCode,
	a9ControllerNumber,
	a9ChannelNumber,
	a9TargetNumber,
	a9EventTimeStamp
    }
          DESCRIPTION
           "Misc error found."
           --#SUMMARY  "[ctl: %d chn: %d tgt: %d :] Misc error found." 
           --#ARGUMENTS {1,2,3}
           --#SEVERITY MINOR
           --#TIMEINDEX 4
           --#STATE OPERATIONAL
           ::= 24

physdevReset    TRAP-TYPE
    ENTERPRISE  eMylexRaidEventInformation
    VARIABLES   {
	a9EventCode,
	a9ControllerNumber,
	a9ChannelNumber,
	a9TargetNumber,
	a9EventTimeStamp
    }
          DESCRIPTION
           "SCSI device reset."
           --#SUMMARY  "[ctl: %d chn: %d tgt: %d :] SCSI device reset." 
           --#ARGUMENTS {1,2,3}
           --#SEVERITY INFORMATIONAL
           --#TIMEINDEX 4
           --#STATE OPERATIONAL
           ::= 25

physdevActivespare    TRAP-TYPE
    ENTERPRISE  eMylexRaidEventInformation
    VARIABLES   {
	a9EventCode,
	a9ControllerNumber,
	a9ChannelNumber,
	a9TargetNumber,
	a9EventTimeStamp
    }
          DESCRIPTION
           "Active spare found."
           --#SUMMARY  "[ctl: %d chn: %d tgt: %d :] Active spare found." 
           --#ARGUMENTS {1,2,3}
           --#SEVERITY INFORMATIONAL
           --#TIMEINDEX 4
           --#STATE OPERATIONAL
           ::= 26

physdevWarmspare    TRAP-TYPE
    ENTERPRISE  eMylexRaidEventInformation
    VARIABLES   {
	a9EventCode,
	a9ControllerNumber,
	a9ChannelNumber,
	a9TargetNumber,
	a9EventTimeStamp
    }
          DESCRIPTION
           "Warm spare found."
           --#SUMMARY  "[ctl: %d chn: %d tgt: %d :] Warm spare found." 
           --#ARGUMENTS {1,2,3}
           --#SEVERITY INFORMATIONAL
           --#TIMEINDEX 4
           --#STATE OPERATIONAL
           ::= 27

physdevReqsense    TRAP-TYPE
    ENTERPRISE  eMylexRaidEventInformation
    VARIABLES   {
	a9EventCode,
	a9ControllerNumber,
	a9ChannelNumber,
	a9TargetNumber,
	a9Lun,
	a9EventTimeStamp
    }
          DESCRIPTION
           "Request Sense Data available."
           --#SUMMARY  "[ctl: %d chn: %d tgt: %d lun: %d :] Request Sense Data available." 
           --#ARGUMENTS {1,2,3,4}
           --#SEVERITY MAJOR
           --#TIMEINDEX 5
           --#STATE DEGRADED
           ::= 28

physdevInitStarted    TRAP-TYPE
    ENTERPRISE  eMylexRaidEventInformation
    VARIABLES   {
	a9EventCode,
	a9ControllerNumber,
	a9ChannelNumber,
	a9TargetNumber,
	a9EventTimeStamp
    }
          DESCRIPTION
           "Initialization started."
           --#SUMMARY  "[ctl: %d chn: %d tgt: %d :] Initialization started." 
           --#ARGUMENTS {1,2,3}
           --#SEVERITY INFORMATIONAL
           --#TIMEINDEX 4
           --#STATE OPERATIONAL
           ::= 29

physdevInitDone    TRAP-TYPE
    ENTERPRISE  eMylexRaidEventInformation
    VARIABLES   {
	a9EventCode,
	a9ControllerNumber,
	a9ChannelNumber,
	a9TargetNumber,
	a9EventTimeStamp
    }
          DESCRIPTION
           "Initialization completed."
           --#SUMMARY  "[ctl: %d chn: %d tgt: %d :] Initialization completed." 
           --#ARGUMENTS {1,2,3}
           --#SEVERITY INFORMATIONAL
           --#TIMEINDEX 4
           --#STATE OPERATIONAL
           ::= 30

physdevInitFailed    TRAP-TYPE
    ENTERPRISE  eMylexRaidEventInformation
    VARIABLES   {
	a9EventCode,
	a9ControllerNumber,
	a9ChannelNumber,
	a9TargetNumber,
	a9EventTimeStamp
    }
          DESCRIPTION
           "Initialization failed."
           --#SUMMARY  "[ctl: %d chn: %d tgt: %d :] Initialization failed." 
           --#ARGUMENTS {1,2,3}
           --#SEVERITY MAJOR
           --#TIMEINDEX 4
           --#STATE DEGRADED
           ::= 31

physdevInitCanceled    TRAP-TYPE
    ENTERPRISE  eMylexRaidEventInformation
    VARIABLES   {
	a9EventCode,
	a9ControllerNumber,
	a9ChannelNumber,
	a9TargetNumber,
	a9EventTimeStamp
    }
          DESCRIPTION
           "Initialization canceled."
           --#SUMMARY  "[ctl: %d chn: %d tgt: %d :] Initialization canceled." 
           --#ARGUMENTS {1,2,3}
           --#SEVERITY MAJOR
           --#TIMEINDEX 4
           --#STATE DEGRADED
           ::= 32

physdevWriterecDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because write recovery failed."
           --#SUMMARY  "[ctl: %d chn: %d tgt: %d :] A physical disk failed because write recovery failed." 
           --#ARGUMENTS {1,2,3}
           --#SEVERITY MAJOR
           --#TIMEINDEX 4
           --#STATE DEGRADED
           ::= 33

physdevResetDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because SCSI bus reset failed."
           --#SUMMARY  "[ctl: %d chn: %d tgt: %d :] A physical disk failed because SCSI bus reset failed." 
           --#ARGUMENTS {1,2,3}
           --#SEVERITY MAJOR
           --#TIMEINDEX 4
           --#STATE DEGRADED
           ::= 34

physdevDblccDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because double check condition occured."
           --#SUMMARY  "[ctl: %d chn: %d tgt: %d :] A physical disk failed because double check condition occured." 
           --#ARGUMENTS {1,2,3}
           --#SEVERITY MAJOR
           --#TIMEINDEX 4
           --#STATE DEGRADED
           ::= 35

physdevRemovedDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because device is missing."
           --#SUMMARY  "[ctl: %d chn: %d tgt: %d :] A physical disk failed because device is missing." 
           --#ARGUMENTS {1,2,3}
           --#SEVERITY MAJOR
           --#TIMEINDEX 4
           --#STATE DEGRADED
           ::= 36

physdevGrosserrDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because of gross error on SCSI processor."
           --#SUMMARY  "[ctl: %d chn: %d tgt: %d :] A physical disk failed because of gross error on SCSI processor." 
           --#ARGUMENTS {1,2,3}
           --#SEVERITY MAJOR
           --#TIMEINDEX 4
           --#STATE DEGRADED
           ::= 37

physdevBadtagDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because of invalid tag."
           --#SUMMARY  "[ctl: %d chn: %d tgt: %d :] A physical disk failed because of invalid tag." 
           --#ARGUMENTS {1,2,3}
           --#SEVERITY MAJOR
           --#TIMEINDEX 4
           --#STATE DEGRADED
           ::= 38

physdevScsitmoDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because a command timed out."
           --#SUMMARY  "[ctl: %d chn: %d tgt: %d :] A physical disk failed because a command timed out." 
           --#ARGUMENTS {1,2,3}
           --#SEVERITY MAJOR
           --#TIMEINDEX 4
           --#STATE DEGRADED
           ::= 39

physdevSysresetDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because of the system reset."
           --#SUMMARY  "[ctl: %d chn: %d tgt: %d :] A physical disk failed because of the system reset." 
           --#ARGUMENTS {1,2,3}
           --#SEVERITY MAJOR
           --#TIMEINDEX 4
           --#STATE DEGRADED
           ::= 40

physdevBsyparDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because of busy status or parity error."
           --#SUMMARY  "[ctl: %d chn: %d tgt: %d :] A physical disk failed because of busy status or parity error." 
           --#ARGUMENTS {1,2,3}
           --#SEVERITY MAJOR
           --#TIMEINDEX 4
           --#STATE DEGRADED
           ::= 41

physdevBycmdDead    TRAP-TYPE
    ENTERPRISE  eMylexRaidEventInformation
    VARIABLES   {
	a9EventCode,
	a9ControllerNumber,
	a9ChannelNumber,
	a9TargetNumber,
	a9EventTimeStamp
    }
          DESCRIPTION
           "A physical disk set to failed state by host."
           --#SUMMARY  "[ctl: %d chn: %d tgt: %d :] A physical disk set to failed state by host." 
           --#ARGUMENTS {1,2,3}
           --#SEVERITY MAJOR
           --#TIMEINDEX 4
           --#STATE DEGRADED
           ::= 42

physdevSeltmoDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because access to the device met with a selection time out."
           --#SUMMARY  "[ctl: %d chn: %d tgt: %d :] A physical disk failed because access to the device met with a selection time out." 
           --#ARGUMENTS {1,2,3}
           --#SEVERITY MAJOR
           --#TIMEINDEX 4
           --#STATE DEGRADED
           ::= 43

physdevSeqerrDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because of a sequence error in the SCSI bus phase handling."
           --#SUMMARY  "[ctl: %d chn: %d tgt: %d :] A physical disk failed because of a sequence error in the SCSI bus phase handling." 
           --#ARGUMENTS {1,2,3}
           --#SEVERITY MAJOR
           --#TIMEINDEX 4
           --#STATE DEGRADED
           ::= 44

physdevUnknownstsDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because device returned an unknown status."
           --#SUMMARY  "[ctl: %d chn: %d tgt: %d :] A physical disk failed because device returned an unknown status." 
           --#ARGUMENTS {1,2,3}
           --#SEVERITY MAJOR
           --#TIMEINDEX 4
           --#STATE DEGRADED
           ::= 45

physdevNotrdyDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because device is not ready."
           --#SUMMARY  "[ctl: %d chn: %d tgt: %d :] A physical disk failed because device is not ready." 
           --#ARGUMENTS {1,2,3}
           --#SEVERITY MAJOR
           --#TIMEINDEX 4
           --#STATE DEGRADED
           ::= 46

physdevMissingDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because device was not found on start up."
           --#SUMMARY  "[ctl: %d chn: %d tgt: %d :] A physical disk failed because device was not found on start up." 
           --#ARGUMENTS {1,2,3}
           --#SEVERITY MAJOR
           --#TIMEINDEX 4
           --#STATE DEGRADED
           ::= 47

physdevCodwrfailDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because write operation of the 'Configuration On Disk' failed."
           --#SUMMARY  "[ctl: %d chn: %d tgt: %d :] A physical disk failed because write operation of the 'Configuration On Disk' failed." 
           --#ARGUMENTS {1,2,3}
           --#SEVERITY MAJOR
           --#TIMEINDEX 4
           --#STATE DEGRADED
           ::= 48

physdevBdtwrfailDead    TRAP-TYPE
    ENTERPRISE  eMylexRaidEventInformation
    VARIABLES   {
	a9EventCode,
	a9ControllerNumber,
	a9ChannelNumber,
	a9TargetNumber,
	a9EventTimeStamp
    }
          DESCRIPTION
           "A physical disk failed because write operation of 'Bad Data Table' failed."
           --#SUMMARY  "[ctl: %d chn: %d tgt: %d :] A physical disk failed because write operation of 'Bad Data Table' failed." 
           --#ARGUMENTS {1,2,3}
           --#SEVERITY MAJOR
           --#TIMEINDEX 4
           --#STATE DEGRADED
           ::= 49

physdevOffline    TRAP-TYPE
    ENTERPRISE  eMylexRaidEventInformation
    VARIABLES   {
	a9EventCode,
	a9ControllerNumber,
	a9ChannelNumber,
	a9TargetNumber,
	a9EventTimeStamp
    }
          DESCRIPTION
           "Physical disk status changed to offline."
           --#SUMMARY  "[ctl: %d chn: %d tgt: %d :] Physical disk status changed to offline." 
           --#ARGUMENTS {1,2,3}
           --#SEVERITY MAJOR
           --#TIMEINDEX 4
           --#STATE DEGRADED
           ::= 50

physdevStandby    TRAP-TYPE
    ENTERPRISE  eMylexRaidEventInformation
    VARIABLES   {
	a9EventCode,
	a9ControllerNumber,
	a9ChannelNumber,
	a9TargetNumber,
	a9EventTimeStamp
    }
          DESCRIPTION
           "Physical disk status changed to hot spare."
           --#SUMMARY  "[ctl: %d chn: %d tgt: %d :] Physical disk status changed to hot spare." 
           --#ARGUMENTS {1,2,3}
           --#SEVERITY INFORMATIONAL
           --#TIMEINDEX 4
           --#STATE OPERATIONAL
           ::= 51

physdevRebuild    TRAP-TYPE
    ENTERPRISE  eMylexRaidEventInformation
    VARIABLES   {
	a9EventCode,
	a9ControllerNumber,
	a9ChannelNumber,
	a9TargetNumber,
	a9EventTimeStamp
    }
          DESCRIPTION
           "Physical disk status changed to rebuild."
           --#SUMMARY  "[ctl: %d chn: %d tgt: %d :] Physical disk status changed to rebuild." 
           --#ARGUMENTS {1,2,3}
           --#SEVERITY MAJOR
           --#TIMEINDEX 4
           --#STATE DEGRADED
           ::= 52

physdevIdMismatch    TRAP-TYPE
    ENTERPRISE  eMylexRaidEventInformation
    VARIABLES   {
	a9EventCode,
	a9ControllerNumber,
	a9ChannelNumber,
	a9TargetNumber,
	a9EventTimeStamp
    }
          DESCRIPTION
           "Physical device ID did not match."
           --#SUMMARY  "[ctl: %d chn: %d tgt: %d :] Physical device ID did not match." 
           --#ARGUMENTS {1,2,3}
           --#SEVERITY MINOR
           --#TIMEINDEX 4
           --#STATE OPERATIONAL
           ::= 53

physdevFailedStart    TRAP-TYPE
    ENTERPRISE  eMylexRaidEventInformation
    VARIABLES   {
	a9EventCode,
	a9ControllerNumber,
	a9ChannelNumber,
	a9TargetNumber,
	a9EventTimeStamp
    }
          DESCRIPTION
           "Physical disk failed to start."
           --#SUMMARY  "[ctl: %d chn: %d tgt: %d :] Physical disk failed to start." 
           --#ARGUMENTS {1,2,3}
           --#SEVERITY MAJOR
           --#TIMEINDEX 4
           --#STATE DEGRADED
           ::= 54

physdevOffsetSet    TRAP-TYPE
    ENTERPRISE  eMylexRaidEventInformation
    VARIABLES   {
	a9EventCode,
	a9ControllerNumber,
	a9ChannelNumber,
	a9TargetNumber,
	a9EventTimeStamp
    }
          DESCRIPTION
           "Physical disk negotiated different offset than config."
           --#SUMMARY  "[ctl: %d chn: %d tgt: %d :] Physical disk negotiated different offset than config." 
           --#ARGUMENTS {1,2,3}
           --#SEVERITY MINOR
           --#TIMEINDEX 4
           --#STATE OPERATIONAL
           ::= 55

physdevSetBusWidth    TRAP-TYPE
    ENTERPRISE  eMylexRaidEventInformation
    VARIABLES   {
	a9EventCode,
	a9ControllerNumber,
	a9ChannelNumber,
	a9TargetNumber,
	a9EventTimeStamp
    }
          DESCRIPTION
           "Physical disk negotiated different bus width than config."
           --#SUMMARY  "[ctl: %d chn: %d tgt: %d :] Physical disk negotiated different bus width than config." 
           --#ARGUMENTS {1,2,3}
           --#SEVERITY MINOR
           --#TIMEINDEX 4
           --#STATE OPERATIONAL
           ::= 56

physdevMissingOnstartup    TRAP-TYPE
    ENTERPRISE  eMylexRaidEventInformation
    VARIABLES   {
	a9EventCode,
	a9ControllerNumber,
	a9ChannelNumber,
	a9TargetNumber,
	a9EventTimeStamp
    }
          DESCRIPTION
           "Physical disk missing on startup."
           --#SUMMARY  "[ctl: %d chn: %d tgt: %d :] Physical disk missing on startup." 
           --#ARGUMENTS {1,2,3}
           --#SEVERITY MAJOR
           --#TIMEINDEX 4
           --#STATE DEGRADED
           ::= 57

physdevRebuildStartFailed    TRAP-TYPE
    ENTERPRISE  eMylexRaidEventInformation
    VARIABLES   {
	a9EventCode,
	a9ControllerNumber,
	a9ChannelNumber,
	a9TargetNumber,
	a9EventTimeStamp
    }
          DESCRIPTION
           "Rebuild startup failed due to lower physical disk capacity."
           --#SUMMARY  "[ctl: %d chn: %d tgt: %d :] Rebuild startup failed due to lower physical disk capacity." 
           --#ARGUMENTS {1,2,3}
           --#SEVERITY MAJOR
           --#TIMEINDEX 4
           --#STATE DEGRADED
           ::= 58

physdevMovingToOtherChn    TRAP-TYPE
    ENTERPRISE  eMylexRaidEventInformation
    VARIABLES   {
	a9EventCode,
	a9ControllerNumber,
	a9ChannelNumber,
	a9TargetNumber,
	a9EventTimeStamp
    }
          DESCRIPTION
           "Physical disk is switching from one channel to the other channel."
           --#SUMMARY  "[ctl: %d chn: %d tgt: %d :] Physical disk is switching from one channel to the other channel." 
           --#ARGUMENTS {1,2,3}
           --#SEVERITY MAJOR
           --#TIMEINDEX 4
           --#STATE DEGRADED
           ::= 59

physdevOfflineDeviceMadeOnline    TRAP-TYPE
    ENTERPRISE  eMylexRaidEventInformation
    VARIABLES   {
	a9EventCode,
	a9ControllerNumber,
	a9ChannelNumber,
	a9TargetNumber,
	a9EventTimeStamp
    }
          DESCRIPTION
           "Temporary-Dead physical disk is automatically made online."
           --#SUMMARY  "[ctl: %d chn: %d tgt: %d :] Temporary-Dead physical disk is automatically made online." 
           --#ARGUMENTS {1,2,3}
           --#SEVERITY MAJOR
           --#TIMEINDEX 4
           --#STATE DEGRADED
           ::= 60

physdevStandbyRebuildStart    TRAP-TYPE
    ENTERPRISE  eMylexRaidEventInformation
    VARIABLES   {
	a9EventCode,
	a9ControllerNumber,
	a9ChannelNumber,
	a9TargetNumber,
	a9EventTimeStamp
    }
          DESCRIPTION
           "A standby rebuild has started."
           --#SUMMARY  "[ctl: %d chn: %d tgt: %d :] A standby rebuild has started." 
           --#ARGUMENTS {1,2,3}
           --#SEVERITY INFORMATIONAL
           --#TIMEINDEX 4
           --#STATE OPERATIONAL
           ::= 61

physdevHotSpareSmaller    TRAP-TYPE
    ENTERPRISE  eMylexRaidEventInformation
    VARIABLES   {
	a9EventCode,
	a9ControllerNumber,
	a9ChannelNumber,
	a9TargetNumber,
	a9EventTimeStamp
    }
          DESCRIPTION
           "Hot spare replaced with a smaller capacity physical disk."
           --#SUMMARY  "[ctl: %d chn: %d tgt: %d :] Hot spare replaced with a smaller capacity physical disk." 
           --#ARGUMENTS {1,2,3}
           --#SEVERITY INFORMATIONAL
           --#TIMEINDEX 4
           --#STATE OPERATIONAL
           ::= 62

ppilotLogicalDiskOnline    TRAP-TYPE
    ENTERPRISE  eMylexRaidEventInformation
    VARIABLES   {
	a9EventCode,
	a9EventTimeStamp
    }
          DESCRIPTION
           "A storage access path has come online."
           --#SUMMARY  "    A storage access path has come online." 
           --#ARGUMENTS {}
           --#SEVERITY INFORMATIONAL
           --#TIMEINDEX 1
           --#STATE OPERATIONAL
           ::= 63

ppilotLogicalDiskOffline    TRAP-TYPE
    ENTERPRISE  eMylexRaidEventInformation
    VARIABLES   {
	a9EventCode,
	a9EventTimeStamp
    }
          DESCRIPTION
           "A storage access path has been lost."
           --#SUMMARY  "    A storage access path has been lost." 
           --#ARGUMENTS {}
           --#SEVERITY MAJOR
           --#TIMEINDEX 1
           --#STATE DEGRADED
           ::= 64

ppilotLogicalDiskPathFailover    TRAP-TYPE
    ENTERPRISE  eMylexRaidEventInformation
    VARIABLES   {
	a9EventCode,
	a9EventTimeStamp
    }
          DESCRIPTION
           "A storage access path has shifted to the alternate path."
           --#SUMMARY  "    A storage access path has shifted to the alternate path." 
           --#ARGUMENTS {}
           --#SEVERITY MAJOR
           --#TIMEINDEX 1
           --#STATE DEGRADED
           ::= 65

ppilotLogicalDiskPathFailback    TRAP-TYPE
    ENTERPRISE  eMylexRaidEventInformation
    VARIABLES   {
	a9EventCode,
	a9EventTimeStamp
    }
          DESCRIPTION
           "A storage access path has shifted to the primary path."
           --#SUMMARY  "    A storage access path has shifted to the primary path." 
           --#ARGUMENTS {}
           --#SEVERITY INFORMATIONAL
           --#TIMEINDEX 1
           --#STATE OPERATIONAL
           ::= 66

physdevNonRedundantAccess    TRAP-TYPE
    ENTERPRISE  eMylexRaidEventInformation
    VARIABLES   {
	a9EventCode,
	a9ControllerNumber,
	a9ChannelNumber,
	a9TargetNumber,
	a9EventTimeStamp
    }
          DESCRIPTION
           "Physical Disk found on only one disk channel."
           --#SUMMARY  "[ctl: %d chn: %d tgt: %d :] Physical Disk found on only one disk channel." 
           --#ARGUMENTS {1,2,3}
           --#SEVERITY MAJOR
           --#TIMEINDEX 4
           --#STATE DEGRADED
           ::= 67

physdevTypeInvalid    TRAP-TYPE
    ENTERPRISE  eMylexRaidEventInformation
    VARIABLES   {
	a9EventCode,
	a9ControllerNumber,
	a9ChannelNumber,
	a9TargetNumber,
	a9EventTimeStamp
    }
          DESCRIPTION
           "Physical disk type is not approved by vendor."
           --#SUMMARY  "[ctl: %d chn: %d tgt: %d :] Physical disk type is not approved by vendor." 
           --#ARGUMENTS {1,2,3}
           --#SEVERITY INFORMATIONAL
           --#TIMEINDEX 4
           --#STATE OPERATIONAL
           ::= 68

physdevSoftId    TRAP-TYPE
    ENTERPRISE  eMylexRaidEventInformation
    VARIABLES   {
	a9EventCode,
	a9ControllerNumber,
	a9ChannelNumber,
	a9TargetNumber,
	a9EventTimeStamp
    }
          DESCRIPTION
           "Physical disk has acquired an inappropriate loop ID. Enclosure disk-slot operations are disabled while this condition persists."
           --#SUMMARY  "[ctl: %d chn: %d tgt: %d :] Physical disk has acquired an inappropriate loop ID. Enclosure disk-slot operations are disabled while this condition persists." 
           --#ARGUMENTS {1,2,3}
           --#SEVERITY MAJOR
           --#TIMEINDEX 4
           --#STATE DEGRADED
           ::= 69

physdevPortFailed    TRAP-TYPE
    ENTERPRISE  eMylexRaidEventInformation
    VARIABLES   {
	a9EventCode,
	a9ControllerNumber,
	a9ChannelNumber,
	a9TargetNumber,
	a9EventTimeStamp
    }
          DESCRIPTION
           "Physical disk port has failed or cannot operate at the configured channel speed."
           --#SUMMARY  "[ctl: %d chn: %d tgt: %d :] Physical disk port has failed or cannot operate at the configured channel speed." 
           --#ARGUMENTS {1,2,3}
           --#SEVERITY MAJOR
           --#TIMEINDEX 4
           --#STATE DEGRADED
           ::= 70

ctldevMirrorRaceEntryFailed    TRAP-TYPE
    ENTERPRISE  eMylexRaidEventInformation
    VARIABLES   {
	a9EventCode,
	a9ControllerNumber,
	a9LogicalDriveNumber,
	a9EventTimeStamp
    }
          DESCRIPTION
           "Mirror Race recovery failed for logical drive."
           --#SUMMARY  "[ctl: %d logdrv: %d :] Mirror Race recovery failed for logical drive." 
           --#ARGUMENTS {1,2}
           --#SEVERITY MAJOR
           --#TIMEINDEX 3
           --#STATE DEGRADED
           ::= 71

ctldevCtrlParamsChecksumFailed    TRAP-TYPE
    ENTERPRISE  eMylexRaidEventInformation
    VARIABLES   {
	a9EventCode,
	a9ControllerNumber,
	a9EventTimeStamp
    }
          DESCRIPTION
           "Controller parameters checksum verification failed - restored default."
           --#SUMMARY  "[ctl: %d :] Controller parameters checksum verification failed - restored default." 
           --#ARGUMENTS {1}
           --#SEVERITY MAJOR
           --#TIMEINDEX 2
           --#STATE DEGRADED
           ::= 72

firmwareUpgradeStarted    TRAP-TYPE
    ENTERPRISE  eMylexRaidEventInformation
    VARIABLES   {
	a9EventCode,
	a9ControllerNumber,
	a9EventTimeStamp
    }
          DESCRIPTION
           "Online controller firmware upgrade has started."
           --#SUMMARY  "[ctl: %d :] Online controller firmware upgrade has started." 
           --#ARGUMENTS {1}
           --#SEVERITY INFORMATIONAL
           --#TIMEINDEX 2
           --#STATE OPERATIONAL
           ::= 73

firmwareUpgradeComplete    TRAP-TYPE
    ENTERPRISE  eMylexRaidEventInformation
    VARIABLES   {
	a9EventCode,
	a9ControllerNumber,
	a9EventTimeStamp
    }
          DESCRIPTION
           "Online firmware upgrade has completed successfully."
           --#SUMMARY  "[ctl: %d :] Online firmware upgrade has completed successfully." 
           --#ARGUMENTS {1}
           --#SEVERITY INFORMATIONAL
           --#TIMEINDEX 2
           --#STATE OPERATIONAL
           ::= 74

firmwareUpgradeFailed    TRAP-TYPE
    ENTERPRISE  eMylexRaidEventInformation
    VARIABLES   {
	a9EventCode,
	a9ControllerNumber,
	a9EventTimeStamp
    }
          DESCRIPTION
           "Online firmware upgrade has failed."
           --#SUMMARY  "[ctl: %d :] Online firmware upgrade has failed." 
           --#ARGUMENTS {1}
           --#SEVERITY MAJOR
           --#TIMEINDEX 2
           --#STATE DEGRADED
           ::= 75

cfgCodDropped    TRAP-TYPE
    ENTERPRISE  eMylexRaidEventInformation
    VARIABLES   {
	a9EventCode,
	a9ControllerNumber,
	a9EventTimeStamp
    }
          DESCRIPTION
           "A Configuration On Disk (COD) with unsupported features has been detected."
           --#SUMMARY  "[ctl: %d :] A Configuration On Disk (COD) with unsupported features has been detected." 
           --#ARGUMENTS {1}
           --#SEVERITY INFORMATIONAL
           --#TIMEINDEX 2
           --#STATE OPERATIONAL
           ::= 76

ctldevBbuNewBattery    TRAP-TYPE
    ENTERPRISE  eMylexRaidEventInformation
    VARIABLES   {
	a9EventCode,
	a9ControllerNumber,
	a9EventTimeStamp
    }
          DESCRIPTION
           "New battery found."
           --#SUMMARY  "[ctl: %d :] New battery found." 
           --#ARGUMENTS {1}
           --#SEVERITY INFORMATIONAL
           --#TIMEINDEX 2
           --#STATE OPERATIONAL
           ::= 77

ctldevBbuChargerError    TRAP-TYPE
    ENTERPRISE  eMylexRaidEventInformation
    VARIABLES   {
	a9EventCode,
	a9ControllerNumber,
	a9EventTimeStamp
    }
          DESCRIPTION
           "Battery backup unit charger error."
           --#SUMMARY  "[ctl: %d :] Battery backup unit charger error." 
           --#ARGUMENTS {1}
           --#SEVERITY MAJOR
           --#TIMEINDEX 2
           --#STATE DEGRADED
           ::= 78

ctldevBbuBatteryError    TRAP-TYPE
    ENTERPRISE  eMylexRaidEventInformation
    VARIABLES   {
	a9EventCode,
	a9ControllerNumber,
	a9EventTimeStamp
    }
          DESCRIPTION
           "Battery will not hold a charge."
           --#SUMMARY  "[ctl: %d :] Battery will not hold a charge." 
           --#ARGUMENTS {1}
           --#SEVERITY MAJOR
           --#TIMEINDEX 2
           --#STATE DEGRADED
           ::= 79

fwEnteredUnexpectedState    TRAP-TYPE
    ENTERPRISE  eMylexRaidEventInformation
    VARIABLES   {
	a9EventCode,
	a9ControllerNumber,
	a9EventTimeStamp
    }
          DESCRIPTION
           "Firmware entered unexpected state at run-time."
           --#SUMMARY  "[ctl: %d :] Firmware entered unexpected state at run-time." 
           --#ARGUMENTS {1}
           --#SEVERITY MAJOR
           --#TIMEINDEX 2
           --#STATE DEGRADED
           ::= 80

sysdevRebuildFailedOnPartner    TRAP-TYPE
    ENTERPRISE  eMylexRaidEventInformation
    VARIABLES   {
	a9EventCode,
	a9ControllerNumber,
	a9LogicalDriveNumber,
	a9EventTimeStamp
    }
          DESCRIPTION
           "Rebuild stopped on controller failure."
           --#SUMMARY  "[ctl: %d logdrv: %d :] Rebuild stopped on controller failure." 
           --#ARGUMENTS {1,2}
           --#SEVERITY INFORMATIONAL
           --#TIMEINDEX 3
           --#STATE OPERATIONAL
           ::= 81

sysdevCheckConsistencyFailedOnPartner    TRAP-TYPE
    ENTERPRISE  eMylexRaidEventInformation
    VARIABLES   {
	a9EventCode,
	a9ControllerNumber,
	a9LogicalDriveNumber,
	a9EventTimeStamp
    }
          DESCRIPTION
           "Check Consistency stopped on controller failure."
           --#SUMMARY  "[ctl: %d logdrv: %d :] Check Consistency stopped on controller failure." 
           --#ARGUMENTS {1,2}
           --#SEVERITY MAJOR
           --#TIMEINDEX 3
           --#STATE DEGRADED
           ::= 82

sysdevForegroundInitFailedOnPartner    TRAP-TYPE
    ENTERPRISE  eMylexRaidEventInformation
    VARIABLES   {
	a9EventCode,
	a9ControllerNumber,
	a9LogicalDriveNumber,
	a9EventTimeStamp
    }
          DESCRIPTION
           "Foreground Init stopped on controller failure."
           --#SUMMARY  "[ctl: %d logdrv: %d :] Foreground Init stopped on controller failure." 
           --#ARGUMENTS {1,2}
           --#SEVERITY MAJOR
           --#TIMEINDEX 3
           --#STATE DEGRADED
           ::= 83

sysdevBackgroundInitFailedOnPartner    TRAP-TYPE
    ENTERPRISE  eMylexRaidEventInformation
    VARIABLES   {
	a9EventCode,
	a9ControllerNumber,
	a9LogicalDriveNumber,
	a9EventTimeStamp
    }
          DESCRIPTION
           "Background Init stopped on controller failure."
           --#SUMMARY  "[ctl: %d logdrv: %d :] Background Init stopped on controller failure." 
           --#ARGUMENTS {1,2}
           --#SEVERITY INFORMATIONAL
           --#TIMEINDEX 3
           --#STATE OPERATIONAL
           ::= 84

physdevUnrecoverableError    TRAP-TYPE
    ENTERPRISE  eMylexRaidEventInformation
    VARIABLES   {
	a9EventCode,
	a9ControllerNumber,
	a9ChannelNumber,
	a9TargetNumber,
	a9EventTimeStamp
    }
          DESCRIPTION
           "Unable to recover medium error during patrol read."
           --#SUMMARY  "[ctl: %d chn: %d tgt: %d :] Unable to recover medium error during patrol read." 
           --#ARGUMENTS {1,2,3}
           --#SEVERITY INFORMATIONAL
           --#TIMEINDEX 4
           --#STATE OPERATIONAL
           ::= 85

physdevRebuildResume    TRAP-TYPE
    ENTERPRISE  eMylexRaidEventInformation
    VARIABLES   {
	a9EventCode,
	a9ControllerNumber,
	a9ChannelNumber,
	a9TargetNumber,
	a9EventTimeStamp
    }
          DESCRIPTION
           "Rebuild resumed."
           --#SUMMARY  "[ctl: %d chn: %d tgt: %d :] Rebuild resumed." 
           --#ARGUMENTS {1,2,3}
           --#SEVERITY INFORMATIONAL
           --#TIMEINDEX 4
           --#STATE OPERATIONAL
           ::= 86

physdevPatrolreadMovedNxtTgt    TRAP-TYPE
    ENTERPRISE  eMylexRaidEventInformation
    VARIABLES   {
	a9EventCode,
	a9ControllerNumber,
	a9ChannelNumber,
	a9TargetNumber,
	a9EventTimeStamp
    }
          DESCRIPTION
           "Patrol Read operation moved to next available target."
           --#SUMMARY  "[ctl: %d chn: %d tgt: %d :] Patrol Read operation moved to next available target." 
           --#ARGUMENTS {1,2,3}
           --#SEVERITY INFORMATIONAL
           --#TIMEINDEX 4
           --#STATE OPERATIONAL
           ::= 87

physdevPatrolreadMovedNxtChn    TRAP-TYPE
    ENTERPRISE  eMylexRaidEventInformation
    VARIABLES   {
	a9EventCode,
	a9ControllerNumber,
	a9ChannelNumber,
	a9EventTimeStamp
    }
          DESCRIPTION
           "Patrol Read operation moved to next available channel."
           --#SUMMARY  "[ctl: %d chn: %d :] Patrol Read operation moved to next available channel." 
           --#ARGUMENTS {1,2}
           --#SEVERITY INFORMATIONAL
           --#TIMEINDEX 3
           --#STATE OPERATIONAL
           ::= 88

physdevTgtSpeedChange    TRAP-TYPE
    ENTERPRISE  eMylexRaidEventInformation
    VARIABLES   {
	a9EventCode,
	a9ControllerNumber,
	a9ChannelNumber,
	a9TargetNumber,
	a9EventTimeStamp
    }
          DESCRIPTION
           "Physical disk transfer speed changed."
           --#SUMMARY  "[ctl: %d chn: %d tgt: %d :] Physical disk transfer speed changed." 
           --#ARGUMENTS {1,2,3}
           --#SEVERITY INFORMATIONAL
           --#TIMEINDEX 4
           --#STATE OPERATIONAL
           ::= 89

chnSuspended    TRAP-TYPE
    ENTERPRISE  eMylexRaidEventInformation
    VARIABLES   {
	a9EventCode,
	a9ControllerNumber,
	a9ChannelNumber,
	a9EventTimeStamp
    }
          DESCRIPTION
           "Channel is suspended due to some faults."
           --#SUMMARY  "[ctl: %d chn: %d :] Channel is suspended due to cable faults." 
           --#ARGUMENTS {1,2}
           --#SEVERITY MAJOR
           --#TIMEINDEX 3
           --#STATE DEGRADED
           ::= 90

replacedPhysdevSmaller    TRAP-TYPE
    ENTERPRISE  eMylexRaidEventInformation
    VARIABLES   {
	a9EventCode,
	a9ControllerNumber,
	a9ChannelNumber,
	a9TargetNumber,
	a9EventTimeStamp
    }
          DESCRIPTION
           "Configured physical disk replaced by user by a smaller capacity disk."
           --#SUMMARY  "[ctl: %d chn: %d tgt: %d :] Configured physical disk replaced by user by a smaller capacity disk." 
           --#ARGUMENTS {1,2,3}
           --#SEVERITY INFORMATIONAL
           --#TIMEINDEX 4
           --#STATE OPERATIONAL
           ::= 95

fibredevLoopidSoftaddrOccurred    TRAP-TYPE
    ENTERPRISE  eMylexRaidEventInformation
    VARIABLES   {
	a9EventCode,
	a9ControllerNumber,
	a9ChannelNumber,
	a9EventTimeStamp
    }
          DESCRIPTION
           "Device loop ID conflict (soft addressing) detected."
           --#SUMMARY  "[ctl: %d chn: %d :] Device loop ID conflict (soft addressing) detected." 
           --#ARGUMENTS {1,2}
           --#SEVERITY MAJOR
           --#TIMEINDEX 3
           --#STATE DEGRADED
           ::= 96

physClearAborted    TRAP-TYPE
    ENTERPRISE  eMylexRaidEventInformation
    VARIABLES   {
	a9EventCode,
	a9ControllerNumber,
	a9ChannelNumber,
	a9TargetNumber,
	a9EventTimeStamp
    }
          DESCRIPTION
           "PD Clear aborted."
           --#SUMMARY  "[ctl: %d chn: %d tgt: %d :] PD Clear aborted." 
           --#ARGUMENTS {1,2,3}
           --#SEVERITY INFORMATIONAL
           --#TIMEINDEX 4
           --#STATE OPERATIONAL
           ::= 97

physdevClearFailed    TRAP-TYPE
    ENTERPRISE  eMylexRaidEventInformation
    VARIABLES   {
	a9EventCode,
	a9ControllerNumber,
	a9ChannelNumber,
	a9TargetNumber,
	a9EventTimeStamp
    }
          DESCRIPTION
           "PD Clear failed."
           --#SUMMARY  "[ctl: %d chn: %d tgt: %d :] PD Clear failed." 
           --#ARGUMENTS {1,2,3}
           --#SEVERITY MAJOR
           --#TIMEINDEX 4
           --#STATE OPERATIONAL
           ::= 98

physdevClearStarted    TRAP-TYPE
    ENTERPRISE  eMylexRaidEventInformation
    VARIABLES   {
	a9EventCode,
	a9ControllerNumber,
	a9ChannelNumber,
	a9TargetNumber,
	a9EventTimeStamp
    }
          DESCRIPTION
           "PD Clear started."
           --#SUMMARY  "[ctl: %d chn: %d tgt: %d :] PD Clear started." 
           --#ARGUMENTS {1,2,3}
           --#SEVERITY INFORMATIONAL
           --#TIMEINDEX 4
           --#STATE OPERATIONAL
           ::= 99

physdevClearDone    TRAP-TYPE
    ENTERPRISE  eMylexRaidEventInformation
    VARIABLES   {
	a9EventCode,
	a9ControllerNumber,
	a9ChannelNumber,
	a9TargetNumber,
	a9EventTimeStamp
    }
          DESCRIPTION
           "PD Clear completed."
           --#SUMMARY  "[ctl: %d chn: %d tgt: %d :] PD Clear completed." 
           --#ARGUMENTS {1,2,3}
           --#SEVERITY INFORMATIONAL
           --#TIMEINDEX 4
           --#STATE OPERATIONAL
           ::= 100

physdevError    TRAP-TYPE
    ENTERPRISE  eMylexRaidEventInformation
    VARIABLES   {
	a9EventCode,
	a9ControllerNumber,
	a9ChannelNumber,
	a9TargetNumber,
	a9EventTimeStamp
    }
          DESCRIPTION
           "Error."
           --#SUMMARY  "[ctl: %d chn: %d tgt: %d :] Error." 
           --#ARGUMENTS {1,2,3}
           --#SEVERITY MAJOR
           --#TIMEINDEX 4
           --#STATE OPERATIONAL
           ::= 101

physdevHsSmartpollFailed    TRAP-TYPE
    ENTERPRISE  eMylexRaidEventInformation
    VARIABLES   {
	a9EventCode,
	a9ControllerNumber,
	a9ChannelNumber,
	a9TargetNumber,
	a9EventTimeStamp
    }
          DESCRIPTION
           "Hot Spare SMART polling failed."
           --#SUMMARY  "[ctl: %d chn: %d tgt: %d :] Hot Spare SMART polling failed." 
           --#ARGUMENTS {1,2,3}
           --#SEVERITY MAJOR
           --#TIMEINDEX 4
           --#STATE OPERATIONAL
           ::= 102

physdevPrCorrected    TRAP-TYPE
    ENTERPRISE  eMylexRaidEventInformation
    VARIABLES   {
	a9EventCode,
	a9ControllerNumber,
	a9ChannelNumber,
	a9TargetNumber,
	a9EventTimeStamp
    }
          DESCRIPTION
           "Patrol Read corrected medium error."
           --#SUMMARY  "[ctl: %d chn: %d tgt: %d :] Patrol Read corrected medium error." 
           --#ARGUMENTS {1,2,3}
           --#SEVERITY INFORMATIONAL
           --#TIMEINDEX 4
           --#STATE OPERATIONAL
           ::= 103

physdevReassignWriteFailed    TRAP-TYPE
    ENTERPRISE  eMylexRaidEventInformation
    VARIABLES   {
	a9EventCode,
	a9ControllerNumber,
	a9ChannelNumber,
	a9TargetNumber,
	a9EventTimeStamp
    }
          DESCRIPTION
           "Reassign write operaiton failed."
           --#SUMMARY  "[ctl: %d chn: %d tgt: %d :] Reassign write operaiton failed." 
           --#ARGUMENTS {1,2,3}
           --#SEVERITY MAJOR
           --#TIMEINDEX 4
           --#STATE OPERATIONAL
           ::= 104

physdevRbldMediumError    TRAP-TYPE
    ENTERPRISE  eMylexRaidEventInformation
    VARIABLES   {
	a9EventCode,
	a9ControllerNumber,
	a9ChannelNumber,
	a9TargetNumber,
	a9EventTimeStamp
    }
          DESCRIPTION
           "Unrecoverable medium error during rebuild."
           --#SUMMARY  "[ctl: %d chn: %d tgt: %d :] Unrecoverable medium error during rebuild." 
           --#ARGUMENTS {1,2,3}
           --#SEVERITY MAJOR
           --#TIMEINDEX 4
           --#STATE OPERATIONAL
           ::= 105

physdevRecCorrecting    TRAP-TYPE
    ENTERPRISE  eMylexRaidEventInformation
    VARIABLES   {
	a9EventCode,
	a9ControllerNumber,
	a9ChannelNumber,
	a9TargetNumber,
	a9EventTimeStamp
    }
          DESCRIPTION
           "Corrected medium error during recovery."
           --#SUMMARY  "[ctl: %d chn: %d tgt: %d :] Corrected medium error during recovery." 
           --#ARGUMENTS {1,2,3}
           --#SEVERITY INFORMATIONAL
           --#TIMEINDEX 4
           --#STATE OPERATIONAL
           ::= 106

physdevRecoverMediumError    TRAP-TYPE
    ENTERPRISE  eMylexRaidEventInformation
    VARIABLES   {
	a9EventCode,
	a9ControllerNumber,
	a9ChannelNumber,
	a9TargetNumber,
	a9EventTimeStamp
    }
          DESCRIPTION
           "Unrecoverable medium error during recovery."
           --#SUMMARY  "[ctl: %d chn: %d tgt: %d :] Unrecoverable medium error during recovery." 
           --#ARGUMENTS {1,2,3}
           --#SEVERITY MAJOR
           --#TIMEINDEX 4
           --#STATE OPERATIONAL
           ::= 107

physdevRedundantPathBroken    TRAP-TYPE
    ENTERPRISE  eMylexRaidEventInformation
    VARIABLES   {
	a9EventCode,
	a9ControllerNumber,
	a9ChannelNumber,
	a9TargetNumber,
	a9EventTimeStamp
    }
          DESCRIPTION
           "Redundant path broken."
           --#SUMMARY  "[ctl: %d chn: %d tgt: %d :] Redundant path broken." 
           --#ARGUMENTS {1,2,3}
           --#SEVERITY MINOR
           --#TIMEINDEX 4
           --#STATE OPERATIONAL
           ::= 108

physdevRedundantPathRestored    TRAP-TYPE
    ENTERPRISE  eMylexRaidEventInformation
    VARIABLES   {
	a9EventCode,
	a9ControllerNumber,
	a9ChannelNumber,
	a9TargetNumber,
	a9EventTimeStamp
    }
          DESCRIPTION
           "Redundant path restored."
           --#SUMMARY  "[ctl: %d chn: %d tgt: %d :] Redundant path restored." 
           --#ARGUMENTS {1,2,3}
           --#SEVERITY INFORMATIONAL
           --#TIMEINDEX 4
           --#STATE OPERATIONAL
           ::= 109

physdevDedicatedSpareNoLongerUseful    TRAP-TYPE
    ENTERPRISE  eMylexRaidEventInformation
    VARIABLES   {
	a9EventCode,
	a9ControllerNumber,
	a9ChannelNumber,
	a9TargetNumber,
	a9EventTimeStamp
    }
          DESCRIPTION
           "Dedicated Hot Spare no longer useful due to deleted array."
           --#SUMMARY  "[ctl: %d chn: %d tgt: %d :] Dedicated Hot Spare no longer useful due to deleted array." 
           --#ARGUMENTS {1,2,3}
           --#SEVERITY INFORMATIONAL
           --#TIMEINDEX 4
           --#STATE OPERATIONAL
           ::= 110

physdevDedicatedSpareCreated    TRAP-TYPE
    ENTERPRISE  eMylexRaidEventInformation
    VARIABLES   {
	a9EventCode,
	a9ControllerNumber,
	a9ChannelNumber,
	a9TargetNumber,
	a9EventTimeStamp
    }
          DESCRIPTION
           "Dedicated Hot Spare created."
           --#SUMMARY  "[ctl: %d chn: %d tgt: %d :] Dedicated Hot Spare created." 
           --#ARGUMENTS {1,2,3}
           --#SEVERITY INFORMATIONAL
           --#TIMEINDEX 4
           --#STATE OPERATIONAL
           ::= 111

physdevDedicatedSpareDisabled    TRAP-TYPE
    ENTERPRISE  eMylexRaidEventInformation
    VARIABLES   {
	a9EventCode,
	a9ControllerNumber,
	a9ChannelNumber,
	a9TargetNumber,
	a9EventTimeStamp
    }
          DESCRIPTION
           "Dedicated Hot Spare disabled."
           --#SUMMARY  "[ctl: %d chn: %d tgt: %d :] Dedicated Hot Spare disabled." 
           --#ARGUMENTS {1,2,3}
           --#SEVERITY MINOR
           --#TIMEINDEX 4
           --#STATE OPERATIONAL
           ::= 112

physdevDedicatedSpareNotUsefulForAll    TRAP-TYPE
    ENTERPRISE  eMylexRaidEventInformation
    VARIABLES   {
	a9EventCode,
	a9ControllerNumber,
	a9ChannelNumber,
	a9TargetNumber,
	a9EventTimeStamp
    }
          DESCRIPTION
           "Dedicated Hot Spare no longer useful for all arrays."
           --#SUMMARY  "[ctl: %d chn: %d tgt: %d :] Dedicated Hot Spare no longer useful for all arrays." 
           --#ARGUMENTS {1,2,3}
           --#SEVERITY INFORMATIONAL
           --#TIMEINDEX 4
           --#STATE OPERATIONAL
           ::= 113

physdevGlobalSpareCreated    TRAP-TYPE
    ENTERPRISE  eMylexRaidEventInformation
    VARIABLES   {
	a9EventCode,
	a9ControllerNumber,
	a9ChannelNumber,
	a9TargetNumber,
	a9EventTimeStamp
    }
          DESCRIPTION
           "Global Hot Spare created."
           --#SUMMARY  "[ctl: %d chn: %d tgt: %d :] Global Hot Spare created." 
           --#ARGUMENTS {1,2,3}
           --#SEVERITY INFORMATIONAL
           --#TIMEINDEX 4
           --#STATE OPERATIONAL
           ::= 114

physdevGlobalSpareDisabled    TRAP-TYPE
    ENTERPRISE  eMylexRaidEventInformation
    VARIABLES   {
	a9EventCode,
	a9ControllerNumber,
	a9ChannelNumber,
	a9TargetNumber,
	a9EventTimeStamp
    }
          DESCRIPTION
           "Global Hot Spare disabled."
           --#SUMMARY  "[ctl: %d chn: %d tgt: %d :] Global Hot Spare disabled." 
           --#ARGUMENTS {1,2,3}
           --#SEVERITY MINOR
           --#TIMEINDEX 4
           --#STATE OPERATIONAL
           ::= 115

physdevGlobalSpareNotCoveringAll    TRAP-TYPE
    ENTERPRISE  eMylexRaidEventInformation
    VARIABLES   {
	a9EventCode,
	a9ControllerNumber,
	a9ChannelNumber,
	a9TargetNumber,
	a9EventTimeStamp
    }
          DESCRIPTION
           "Global Hot Spare does not cover all arrays."
           --#SUMMARY  "[ctl: %d chn: %d tgt: %d :] Global Hot Spare does not cover all arrays." 
           --#ARGUMENTS {1,2,3}
           --#SEVERITY INFORMATIONAL
           --#TIMEINDEX 4
           --#STATE OPERATIONAL
           ::= 116

physdevFormatComplete    TRAP-TYPE
    ENTERPRISE  eMylexRaidEventInformation
    VARIABLES   {
	a9EventCode,
	a9ControllerNumber,
	a9ChannelNumber,
	a9TargetNumber,
	a9EventTimeStamp
    }
          DESCRIPTION
           "Format complete."
           --#SUMMARY  "[ctl: %d chn: %d tgt: %d :] Format complete." 
           --#ARGUMENTS {1,2,3}
           --#SEVERITY INFORMATIONAL
           --#TIMEINDEX 4
           --#STATE OPERATIONAL
           ::= 117

physdevFormatStarted    TRAP-TYPE
    ENTERPRISE  eMylexRaidEventInformation
    VARIABLES   {
	a9EventCode,
	a9ControllerNumber,
	a9ChannelNumber,
	a9TargetNumber,
	a9EventTimeStamp
    }
          DESCRIPTION
           "Format started."
           --#SUMMARY  "[ctl: %d chn: %d tgt: %d :] Format started." 
           --#ARGUMENTS {1,2,3}
           --#SEVERITY INFORMATIONAL
           --#TIMEINDEX 4
           --#STATE OPERATIONAL
           ::= 118

physdevTooSmallForAutoRbld    TRAP-TYPE
    ENTERPRISE  eMylexRaidEventInformation
    VARIABLES   {
	a9EventCode,
	a9ControllerNumber,
	a9ChannelNumber,
	a9TargetNumber,
	a9EventTimeStamp
    }
          DESCRIPTION
           "PD too small to be used for auto-rebuild."
           --#SUMMARY  "[ctl: %d chn: %d tgt: %d :] PD too small to be used for auto-rebuild." 
           --#ARGUMENTS {1,2,3}
           --#SEVERITY MINOR
           --#TIMEINDEX 4
           --#STATE OPERATIONAL
           ::= 119

physdevBbmLog80PercentFull    TRAP-TYPE
    ENTERPRISE  eMylexRaidEventInformation
    VARIABLES   {
	a9EventCode,
	a9ControllerNumber,
	a9ChannelNumber,
	a9TargetNumber,
	a9EventTimeStamp
    }
          DESCRIPTION
           "Bad block table on PD is 80% full."
           --#SUMMARY  "[ctl: %d chn: %d tgt: %d :] Bad block table on PD is 80% full." 
           --#ARGUMENTS {1,2,3}
           --#SEVERITY MINOR
           --#TIMEINDEX 4
           --#STATE OPERATIONAL
           ::= 120

physdevBbmLogFull    TRAP-TYPE
    ENTERPRISE  eMylexRaidEventInformation
    VARIABLES   {
	a9EventCode,
	a9ControllerNumber,
	a9ChannelNumber,
	a9TargetNumber,
	a9EventTimeStamp
    }
          DESCRIPTION
           "Bad block table on PD is full; unable to log blocks."
           --#SUMMARY  "[ctl: %d chn: %d tgt: %d :] Bad block table on PD is full; unable to log blocks." 
           --#ARGUMENTS {1,2,3}
           --#SEVERITY MAJOR
           --#TIMEINDEX 4
           --#STATE OPERATIONAL
           ::= 121


physdevMediaerrorCorrected    TRAP-TYPE
    ENTERPRISE  eMylexRaidEventInformation
    VARIABLES   {
	a9EventCode,
	a9ControllerNumber,
	a9ChannelNumber,
	a9TargetNumber,
	a9EventTimeStamp
    }
          DESCRIPTION
           "Firmware corrected the 'Read' error."
           --#SUMMARY  "[ctl: %d chn: %d tgt: %d :] Firmware corrected the 'Read' error." 
           --#ARGUMENTS {1,2,3}
           --#SEVERITY INFORMATIONAL
           --#TIMEINDEX 4
           --#STATE OPERATIONAL
           ::= 126

sysdevCheckDoneWithError    TRAP-TYPE
    ENTERPRISE  eMylexRaidEventInformation
    VARIABLES   {
	a9EventCode,
	a9ControllerNumber,
	a9ChannelNumber,
	a9TargetNumber,
	a9EventTimeStamp
    }
          DESCRIPTION
           "Consistency check is finished with errors."
           --#SUMMARY  "[ctl: %d chn: %d tgt: %d :] Consistency check is finished with errors." 
           --#ARGUMENTS {1,2,3}
           --#SEVERITY INFORMATIONAL
           --#TIMEINDEX 4
           --#STATE OPERATIONAL
           ::= 127

sysdevCheckStart    TRAP-TYPE
    ENTERPRISE  eMylexRaidEventInformation
    VARIABLES   {
	a9EventCode,
	a9ControllerNumber,
	a9LogicalDriveNumber,
	a9EventTimeStamp
    }
          DESCRIPTION
           "Consistency check / Make Data Consistent  is started."
           --#SUMMARY  "[ctl: %d logdrv: %d :] Consistency check / Make Data Consistent  is started." 
           --#ARGUMENTS {1,2}
           --#SEVERITY INFORMATIONAL
           --#TIMEINDEX 3
           --#STATE OPERATIONAL
           ::= 128

sysdevCheckDone    TRAP-TYPE
    ENTERPRISE  eMylexRaidEventInformation
    VARIABLES   {
	a9EventCode,
	a9ControllerNumber,
	a9LogicalDriveNumber,
	a9EventTimeStamp
    }
          DESCRIPTION
           "Consistency check / Make Data Consistent  is finished."
           --#SUMMARY  "[ctl: %d logdrv: %d :] Consistency check / Make Data Consistent  is finished." 
           --#ARGUMENTS {1,2}
           --#SEVERITY INFORMATIONAL
           --#TIMEINDEX 3
           --#STATE OPERATIONAL
           ::= 129

sysdevCheckCanceled    TRAP-TYPE
    ENTERPRISE  eMylexRaidEventInformation
    VARIABLES   {
	a9EventCode,
	a9ControllerNumber,
	a9LogicalDriveNumber,
	a9EventTimeStamp
    }
          DESCRIPTION
           "Consistency check / Make Data Consistent is cancelled."
           --#SUMMARY  "[ctl: %d logdrv: %d :] Consistency check / Make Data Consistent is cancelled." 
           --#ARGUMENTS {1,2}
           --#SEVERITY MAJOR
           --#TIMEINDEX 3
           --#STATE DEGRADED
           ::= 130

sysdevCheckError    TRAP-TYPE
    ENTERPRISE  eMylexRaidEventInformation
    VARIABLES   {
	a9EventCode,
	a9ControllerNumber,
	a9LogicalDriveNumber,
	a9EventTimeStamp
    }
          DESCRIPTION
           "Consistency check on logical drive error."
           --#SUMMARY  "[ctl: %d logdrv: %d :] Consistency check on logical drive error." 
           --#ARGUMENTS {1,2}
           --#SEVERITY MAJOR
           --#TIMEINDEX 3
           --#STATE DEGRADED
           ::= 131

sysdevCheckSysdevFailed    TRAP-TYPE
    ENTERPRISE  eMylexRaidEventInformation
    VARIABLES   {
	a9EventCode,
	a9ControllerNumber,
	a9LogicalDriveNumber,
	a9EventTimeStamp
    }
          DESCRIPTION
           "Consistency check / Make Data Consistent on logical drive failed."
           --#SUMMARY  "[ctl: %d logdrv: %d :] Consistency check / Make Data Consistent on logical drive failed." 
           --#ARGUMENTS {1,2}
           --#SEVERITY MAJOR
           --#TIMEINDEX 3
           --#STATE DEGRADED
           ::= 132

sysdevCheckPhysdevFailed    TRAP-TYPE
    ENTERPRISE  eMylexRaidEventInformation
    VARIABLES   {
	a9EventCode,
	a9ControllerNumber,
	a9LogicalDriveNumber,
	a9EventTimeStamp
    }
          DESCRIPTION
           "Consistency check failed due to physical disk failure."
           --#SUMMARY  "[ctl: %d logdrv: %d :] Consistency check failed due to physical disk failure." 
           --#ARGUMENTS {1,2}
           --#SEVERITY MAJOR
           --#TIMEINDEX 3
           --#STATE DEGRADED
           ::= 133

sysdevOffline    TRAP-TYPE
    ENTERPRISE  eMylexRaidEventInformation
    VARIABLES   {
	a9EventCode,
	a9ControllerNumber,
	a9LogicalDriveNumber,
	a9EventTimeStamp
    }
          DESCRIPTION
           "Logical drive has been made offline."
           --#SUMMARY  "[ctl: %d logdrv: %d :] Logical drive has been made offline." 
           --#ARGUMENTS {1,2}
           --#SEVERITY MAJOR
           --#TIMEINDEX 3
           --#STATE DEGRADED
           ::= 134

sysdevCritical    TRAP-TYPE
    ENTERPRISE  eMylexRaidEventInformation
    VARIABLES   {
	a9EventCode,
	a9ControllerNumber,
	a9LogicalDriveNumber,
	a9EventTimeStamp
    }
          DESCRIPTION
           "Logical drive is critical."
           --#SUMMARY  "[ctl: %d logdrv: %d :] Logical drive is critical." 
           --#ARGUMENTS {1,2}
           --#SEVERITY MAJOR
           --#TIMEINDEX 3
           --#STATE DEGRADED
           ::= 135

sysdevOnline    TRAP-TYPE
    ENTERPRISE  eMylexRaidEventInformation
    VARIABLES   {
	a9EventCode,
	a9ControllerNumber,
	a9LogicalDriveNumber,
	a9EventTimeStamp
    }
          DESCRIPTION
           "Logical drive has been placed online."
           --#SUMMARY  "[ctl: %d logdrv: %d :] Logical drive has been placed online." 
           --#ARGUMENTS {1,2}
           --#SEVERITY INFORMATIONAL
           --#TIMEINDEX 3
           --#STATE OPERATIONAL
           ::= 136

sysdevAutoRebuildStart    TRAP-TYPE
    ENTERPRISE  eMylexRaidEventInformation
    VARIABLES   {
	a9EventCode,
	a9ControllerNumber,
	a9LogicalDriveNumber,
	a9EventTimeStamp
    }
          DESCRIPTION
           "An automatic rebuild has started on logical drive."
           --#SUMMARY  "[ctl: %d logdrv: %d :] An automatic rebuild has started on logical drive." 
           --#ARGUMENTS {1,2}
           --#SEVERITY INFORMATIONAL
           --#TIMEINDEX 3
           --#STATE OPERATIONAL
           ::= 137

sysdevManualRebuildStart    TRAP-TYPE
    ENTERPRISE  eMylexRaidEventInformation
    VARIABLES   {
	a9EventCode,
	a9ControllerNumber,
	a9LogicalDriveNumber,
	a9EventTimeStamp
    }
          DESCRIPTION
           "A manual rebuild has started on logical drive."
           --#SUMMARY  "[ctl: %d logdrv: %d :] A manual rebuild has started on logical drive." 
           --#ARGUMENTS {1,2}
           --#SEVERITY INFORMATIONAL
           --#TIMEINDEX 3
           --#STATE OPERATIONAL
           ::= 138

sysdevRebuildDone    TRAP-TYPE
    ENTERPRISE  eMylexRaidEventInformation
    VARIABLES   {
	a9EventCode,
	a9ControllerNumber,
	a9LogicalDriveNumber,
	a9EventTimeStamp
    }
          DESCRIPTION
           "Rebuild on logical drive is over."
           --#SUMMARY  "[ctl: %d logdrv: %d :] Rebuild on logical drive is over." 
           --#ARGUMENTS {1,2}
           --#SEVERITY INFORMATIONAL
           --#TIMEINDEX 3
           --#STATE OPERATIONAL
           ::= 139

sysdevRebuildCanceled    TRAP-TYPE
    ENTERPRISE  eMylexRaidEventInformation
    VARIABLES   {
	a9EventCode,
	a9ControllerNumber,
	a9LogicalDriveNumber,
	a9EventTimeStamp
    }
          DESCRIPTION
           "Rebuild on logical drive is cancelled."
           --#SUMMARY  "[ctl: %d logdrv: %d :] Rebuild on logical drive is cancelled." 
           --#ARGUMENTS {1,2}
           --#SEVERITY MAJOR
           --#TIMEINDEX 3
           --#STATE DEGRADED
           ::= 140

sysdevRebuildError    TRAP-TYPE
    ENTERPRISE  eMylexRaidEventInformation
    VARIABLES   {
	a9EventCode,
	a9ControllerNumber,
	a9LogicalDriveNumber,
	a9EventTimeStamp
    }
          DESCRIPTION
           "Rebuild stopped with error."
           --#SUMMARY  "[ctl: %d logdrv: %d :] Rebuild stopped with error." 
           --#ARGUMENTS {1,2}
           --#SEVERITY MAJOR
           --#TIMEINDEX 3
           --#STATE DEGRADED
           ::= 141

sysdevRebuildNewdevFailed    TRAP-TYPE
    ENTERPRISE  eMylexRaidEventInformation
    VARIABLES   {
	a9EventCode,
	a9ControllerNumber,
	a9LogicalDriveNumber,
	a9EventTimeStamp
    }
          DESCRIPTION
           "Rebuild stopped with error. New physical disk failed."
           --#SUMMARY  "[ctl: %d logdrv: %d :] Rebuild stopped with error. New physical disk failed." 
           --#ARGUMENTS {1,2}
           --#SEVERITY MAJOR
           --#TIMEINDEX 3
           --#STATE DEGRADED
           ::= 142

sysdevRebuildSysdevFailed    TRAP-TYPE
    ENTERPRISE  eMylexRaidEventInformation
    VARIABLES   {
	a9EventCode,
	a9ControllerNumber,
	a9LogicalDriveNumber,
	a9EventTimeStamp
    }
          DESCRIPTION
           "Rebuild stopped because logical drive failed."
           --#SUMMARY  "[ctl: %d logdrv: %d :] Rebuild stopped because logical drive failed." 
           --#ARGUMENTS {1,2}
           --#SEVERITY MAJOR
           --#TIMEINDEX 3
           --#STATE DEGRADED
           ::= 143

sysdevInitStarted    TRAP-TYPE
    ENTERPRISE  eMylexRaidEventInformation
    VARIABLES   {
	a9EventCode,
	a9ControllerNumber,
	a9LogicalDriveNumber,
	a9EventTimeStamp
    }
          DESCRIPTION
           "Logical drive initialization started."
           --#SUMMARY  "[ctl: %d logdrv: %d :] Logical drive initialization started." 
           --#ARGUMENTS {1,2}
           --#SEVERITY INFORMATIONAL
           --#TIMEINDEX 3
           --#STATE OPERATIONAL
           ::= 144

sysdevInitDone    TRAP-TYPE
    ENTERPRISE  eMylexRaidEventInformation
    VARIABLES   {
	a9EventCode,
	a9ControllerNumber,
	a9LogicalDriveNumber,
	a9EventTimeStamp
    }
          DESCRIPTION
           "Logical drive initialization done."
           --#SUMMARY  "[ctl: %d logdrv: %d :] Logical drive initialization done." 
           --#ARGUMENTS {1,2}
           --#SEVERITY INFORMATIONAL
           --#TIMEINDEX 3
           --#STATE OPERATIONAL
           ::= 145

sysdevInitCanceled    TRAP-TYPE
    ENTERPRISE  eMylexRaidEventInformation
    VARIABLES   {
	a9EventCode,
	a9ControllerNumber,
	a9LogicalDriveNumber,
	a9EventTimeStamp
    }
          DESCRIPTION
           "Logical drive initialization cancelled."
           --#SUMMARY  "[ctl: %d logdrv: %d :] Logical drive initialization cancelled." 
           --#ARGUMENTS {1,2}
           --#SEVERITY MAJOR
           --#TIMEINDEX 3
           --#STATE DEGRADED
           ::= 146

sysdevInitFailed    TRAP-TYPE
    ENTERPRISE  eMylexRaidEventInformation
    VARIABLES   {
	a9EventCode,
	a9ControllerNumber,
	a9LogicalDriveNumber,
	a9EventTimeStamp
    }
          DESCRIPTION
           "Logical drive initialization failed."
           --#SUMMARY  "[ctl: %d logdrv: %d :] Logical drive initialization failed." 
           --#ARGUMENTS {1,2}
           --#SEVERITY MAJOR
           --#TIMEINDEX 3
           --#STATE DEGRADED
           ::= 147

sysdevFound    TRAP-TYPE
    ENTERPRISE  eMylexRaidEventInformation
    VARIABLES   {
	a9EventCode,
	a9ControllerNumber,
	a9LogicalDriveNumber,
	a9EventTimeStamp
    }
          DESCRIPTION
           "A logical drive has been found."
           --#SUMMARY  "[ctl: %d logdrv: %d :] A logical drive has been found." 
           --#ARGUMENTS {1,2}
           --#SEVERITY INFORMATIONAL
           --#TIMEINDEX 3
           --#STATE OPERATIONAL
           ::= 148

sysdevGone    TRAP-TYPE
    ENTERPRISE  eMylexRaidEventInformation
    VARIABLES   {
	a9EventCode,
	a9ControllerNumber,
	a9LogicalDriveNumber,
	a9EventTimeStamp
    }
          DESCRIPTION
           "A logical drive has been deleted."
           --#SUMMARY  "[ctl: %d logdrv: %d :] A logical drive has been deleted." 
           --#ARGUMENTS {1,2}
           --#SEVERITY INFORMATIONAL
           --#TIMEINDEX 3
           --#STATE OPERATIONAL
           ::= 149

sysdevExpandcapacityStart    TRAP-TYPE
    ENTERPRISE  eMylexRaidEventInformation
    VARIABLES   {
	a9EventCode,
	a9ControllerNumber,
	a9LogicalDriveNumber,
	a9EventTimeStamp
    }
          DESCRIPTION
           "Expand capacity started."
           --#SUMMARY  "[ctl: %d logdrv: %d :] Expand capacity started." 
           --#ARGUMENTS {1,2}
           --#SEVERITY INFORMATIONAL
           --#TIMEINDEX 3
           --#STATE OPERATIONAL
           ::= 150

sysdevExpandcapacityDone    TRAP-TYPE
    ENTERPRISE  eMylexRaidEventInformation
    VARIABLES   {
	a9EventCode,
	a9ControllerNumber,
	a9LogicalDriveNumber,
	a9EventTimeStamp
    }
          DESCRIPTION
           "Expand capacity completed."
           --#SUMMARY  "[ctl: %d logdrv: %d :] Expand capacity completed." 
           --#ARGUMENTS {1,2}
           --#SEVERITY INFORMATIONAL
           --#TIMEINDEX 3
           --#STATE OPERATIONAL
           ::= 151

sysdevExpandcapacityError    TRAP-TYPE
    ENTERPRISE  eMylexRaidEventInformation
    VARIABLES   {
	a9EventCode,
	a9ControllerNumber,
	a9LogicalDriveNumber,
	a9EventTimeStamp
    }
          DESCRIPTION
           "Expand capacity stopped with error."
           --#SUMMARY  "[ctl: %d logdrv: %d :] Expand capacity stopped with error." 
           --#ARGUMENTS {1,2}
           --#SEVERITY MAJOR
           --#TIMEINDEX 3
           --#STATE DEGRADED
           ::= 152

sysdevBadblock    TRAP-TYPE
    ENTERPRISE  eMylexRaidEventInformation
    VARIABLES   {
	a9EventCode,
	a9ControllerNumber,
	a9LogicalDriveNumber,
	a9EventTimeStamp
    }
          DESCRIPTION
           "Bad Blocks found."
           --#SUMMARY  "[ctl: %d logdrv: %d :] Bad Blocks found." 
           --#ARGUMENTS {1,2}
           --#SEVERITY MAJOR
           --#TIMEINDEX 3
           --#STATE DEGRADED
           ::= 153

sysdevSizechanged    TRAP-TYPE
    ENTERPRISE  eMylexRaidEventInformation
    VARIABLES   {
	a9EventCode,
	a9ControllerNumber,
	a9LogicalDriveNumber,
	a9EventTimeStamp
    }
          DESCRIPTION
           "Logical drive size changed."
           --#SUMMARY  "[ctl: %d logdrv: %d :] Logical drive size changed." 
           --#ARGUMENTS {1,2}
           --#SEVERITY INFORMATIONAL
           --#TIMEINDEX 3
           --#STATE OPERATIONAL
           ::= 154

sysdevTypechanged    TRAP-TYPE
    ENTERPRISE  eMylexRaidEventInformation
    VARIABLES   {
	a9EventCode,
	a9ControllerNumber,
	a9LogicalDriveNumber,
	a9EventTimeStamp
    }
          DESCRIPTION
           "Logical drive type changed."
           --#SUMMARY  "[ctl: %d logdrv: %d :] Logical drive type changed." 
           --#ARGUMENTS {1,2}
           --#SEVERITY INFORMATIONAL
           --#TIMEINDEX 3
           --#STATE OPERATIONAL
           ::= 155

sysdevBaddatablock    TRAP-TYPE
    ENTERPRISE  eMylexRaidEventInformation
    VARIABLES   {
	a9EventCode,
	a9ControllerNumber,
	a9LogicalDriveNumber,
	a9EventTimeStamp
    }
          DESCRIPTION
           "Bad data blocks found. Possible data loss."
           --#SUMMARY  "[ctl: %d logdrv: %d :] Bad data blocks found. Possible data loss." 
           --#ARGUMENTS {1,2}
           --#SEVERITY MAJOR
           --#TIMEINDEX 3
           --#STATE DEGRADED
           ::= 156

sysdevWrLunMap    TRAP-TYPE
    ENTERPRISE  eMylexRaidEventInformation
    VARIABLES   {
	a9EventCode,
	a9ControllerNumber,
	a9EventTimeStamp
    }
          DESCRIPTION
           "Logical drive LUN mapping has been written to config."
           --#SUMMARY  "[ctl: %d :] Logical drive LUN mapping has been written to config." 
           --#ARGUMENTS {1}
           --#SEVERITY INFORMATIONAL
           --#TIMEINDEX 2
           --#STATE OPERATIONAL
           ::= 157

sysdevDatareadFromBlockInBdt    TRAP-TYPE
    ENTERPRISE  eMylexRaidEventInformation
    VARIABLES   {
	a9EventCode,
	a9ControllerNumber,
	a9LogicalDriveNumber,
	a9EventTimeStamp
    }
          DESCRIPTION
           "Attempt to read data from block that is marked in Bad Data Table."
           --#SUMMARY  "[ctl: %d logdrv: %d :] Attempt to read data from block that is marked in Bad Data Table." 
           --#ARGUMENTS {1,2}
           --#SEVERITY MAJOR
           --#TIMEINDEX 3
           --#STATE DEGRADED
           ::= 158

sysdevDataForBlockLost    TRAP-TYPE
    ENTERPRISE  eMylexRaidEventInformation
    VARIABLES   {
	a9EventCode,
	a9ControllerNumber,
	a9LogicalDriveNumber,
	a9EventTimeStamp
    }
          DESCRIPTION
           "Data for Disk Block has been lost due to Logical Drive problem."
           --#SUMMARY  "[ctl: %d logdrv: %d :] Data for Disk Block has been lost due to Logical Drive problem." 
           --#ARGUMENTS {1,2}
           --#SEVERITY MAJOR
           --#TIMEINDEX 3
           --#STATE DEGRADED
           ::= 159

sysdevOfflineDeviceMadeAvailableWithDataloss    TRAP-TYPE
    ENTERPRISE  eMylexRaidEventInformation
    VARIABLES   {
	a9EventCode,
	a9ControllerNumber,
	a9LogicalDriveNumber,
	a9EventTimeStamp
    }
          DESCRIPTION
           "Temporary-Offline RAID5/RAID3 array is available to the user again with the possibility of data loss in the array."
           --#SUMMARY  "[ctl: %d logdrv: %d :] Temporary-Offline RAID5/RAID3 array is available to the user again with the possibility of data loss in the array." 
           --#ARGUMENTS {1,2}
           --#SEVERITY MAJOR
           --#TIMEINDEX 3
           --#STATE DEGRADED
           ::= 160

sysdevOfflineDeviceMadeAvailable    TRAP-TYPE
    ENTERPRISE  eMylexRaidEventInformation
    VARIABLES   {
	a9EventCode,
	a9ControllerNumber,
	a9LogicalDriveNumber,
	a9EventTimeStamp
    }
          DESCRIPTION
           "Temporary-Offline RAID0+1/RAID1/RAID0/JBOD array is available to the user again."
           --#SUMMARY  "[ctl: %d logdrv: %d :] Temporary-Offline RAID0+1/RAID1/RAID0/JBOD array is available to the user again." 
           --#ARGUMENTS {1,2}
           --#SEVERITY MAJOR
           --#TIMEINDEX 3
           --#STATE DEGRADED
           ::= 161

sysdevStandbyRebuildStart    TRAP-TYPE
    ENTERPRISE  eMylexRaidEventInformation
    VARIABLES   {
	a9EventCode,
	a9ControllerNumber,
	a9LogicalDriveNumber,
	a9EventTimeStamp
    }
          DESCRIPTION
           "A standby rebuild has started on a logical drive."
           --#SUMMARY  "[ctl: %d logdrv: %d :] A standby rebuild has started on a logical drive." 
           --#ARGUMENTS {1,2}
           --#SEVERITY INFORMATIONAL
           --#TIMEINDEX 3
           --#STATE OPERATIONAL
           ::= 162

sysdevExpandcapacityMediumError    TRAP-TYPE
    ENTERPRISE  eMylexRaidEventInformation
    VARIABLES   {
	a9EventCode,
	a9ControllerNumber,
	a9LogicalDriveNumber,
	a9EventTimeStamp
    }
          DESCRIPTION
           "Reconstruct detected uncorrectable double medium errors."
           --#SUMMARY  "[ctl: %d logdrv: %d :] Reconstruct detected uncorrectable double medium errors." 
           --#ARGUMENTS {1,2}
           --#SEVERITY MAJOR
           --#TIMEINDEX 3
           --#STATE OPERATIONAL
           ::= 163

sysdevExpandcapacityResume    TRAP-TYPE
    ENTERPRISE  eMylexRaidEventInformation
    VARIABLES   {
	a9EventCode,
	a9ControllerNumber,
	a9LogicalDriveNumber,
	a9EventTimeStamp
    }
          DESCRIPTION
           "Reconstuction resumed."
           --#SUMMARY  "[ctl: %d logdrv: %d :] Reconstuction resumed." 
           --#ARGUMENTS {1,2}
           --#SEVERITY INFORMATIONAL
           --#TIMEINDEX 3
           --#STATE OPERATIONAL
           ::= 164

sysdevExpandcapacityResumefailed    TRAP-TYPE
    ENTERPRISE  eMylexRaidEventInformation
    VARIABLES   {
	a9EventCode,
	a9ControllerNumber,
	a9LogicalDriveNumber,
	a9EventTimeStamp
    }
          DESCRIPTION
           "Reconstuction resume failed due to configuraiton mismatch."
           --#SUMMARY  "[ctl: %d logdrv: %d :] Reconstuction resume failed due to configuraiton mismatch." 
           --#ARGUMENTS {1,2}
           --#SEVERITY MAJOR
           --#TIMEINDEX 3
           --#STATE OPERATIONAL
           ::= 165

sysdevPropertiesChanged    TRAP-TYPE
    ENTERPRISE  eMylexRaidEventInformation
    VARIABLES   {
	a9EventCode,
	a9ControllerNumber,
	a9LogicalDriveNumber,
	a9EventTimeStamp
    }
          DESCRIPTION
           "LD Properties updated."
           --#SUMMARY  "[ctl: %d logdrv: %d :] LD Properties updated." 
           --#ARGUMENTS {1,2}
           --#SEVERITY INFORMATIONAL
           --#TIMEINDEX 3
           --#STATE OPERATIONAL
           ::= 166

sysdevInconsistentDueAtStartUp    TRAP-TYPE
    ENTERPRISE  eMylexRaidEventInformation
    VARIABLES   {
	a9EventCode,
	a9ControllerNumber,
	a9LogicalDriveNumber,
	a9EventTimeStamp
    }
          DESCRIPTION
           "Marking LD inconsistent due to active writes at shutdown."
           --#SUMMARY  "[ctl: %d logdrv: %d :] Marking LD inconsistent due to active writes at shutdown." 
           --#ARGUMENTS {1,2}
           --#SEVERITY MAJOR
           --#TIMEINDEX 3
           --#STATE OPERATIONAL
           ::= 167

sysdevBgInitStarted    TRAP-TYPE
    ENTERPRISE  eMylexRaidEventInformation
    VARIABLES   {
	a9EventCode,
	a9ControllerNumber,
	a9LogicalDriveNumber,
	a9EventTimeStamp
    }
          DESCRIPTION
           "Logical drive background initialization started."
           --#SUMMARY  "[ctl: %d logdrv: %d :] Logical drive background initialization started." 
           --#ARGUMENTS {1,2}
           --#SEVERITY INFORMATIONAL
           --#TIMEINDEX 3
           --#STATE OPERATIONAL
           ::= 176

sysdevBgInitStopped    TRAP-TYPE
    ENTERPRISE  eMylexRaidEventInformation
    VARIABLES   {
	a9EventCode,
	a9ControllerNumber,
	a9LogicalDriveNumber,
	a9EventTimeStamp
    }
          DESCRIPTION
           "Logical drive background initialization stopped."
           --#SUMMARY  "[ctl: %d logdrv: %d :] Logical drive background initialization stopped." 
           --#ARGUMENTS {1,2}
           --#SEVERITY INFORMATIONAL
           --#TIMEINDEX 3
           --#STATE OPERATIONAL
           ::= 177

sysdevBgInitPaused    TRAP-TYPE
    ENTERPRISE  eMylexRaidEventInformation
    VARIABLES   {
	a9EventCode,
	a9ControllerNumber,
	a9LogicalDriveNumber,
	a9EventTimeStamp
    }
          DESCRIPTION
           "Logical drive background initialization paused."
           --#SUMMARY  "[ctl: %d logdrv: %d :] Logical drive background initialization paused." 
           --#ARGUMENTS {1,2}
           --#SEVERITY INFORMATIONAL
           --#TIMEINDEX 3
           --#STATE OPERATIONAL
           ::= 178

sysdevBgInitRestarted    TRAP-TYPE
    ENTERPRISE  eMylexRaidEventInformation
    VARIABLES   {
	a9EventCode,
	a9ControllerNumber,
	a9LogicalDriveNumber,
	a9EventTimeStamp
    }
          DESCRIPTION
           "Logical drive background initialization restarted."
           --#SUMMARY  "[ctl: %d logdrv: %d :] Logical drive background initialization restarted." 
           --#ARGUMENTS {1,2}
           --#SEVERITY INFORMATIONAL
           --#TIMEINDEX 3
           --#STATE OPERATIONAL
           ::= 179

sysdevBgInitFailed    TRAP-TYPE
    ENTERPRISE  eMylexRaidEventInformation
    VARIABLES   {
	a9EventCode,
	a9ControllerNumber,
	a9LogicalDriveNumber,
	a9EventTimeStamp
    }
          DESCRIPTION
           "Logical drive background initialization failed."
           --#SUMMARY  "[ctl: %d logdrv: %d :] Logical drive background initialization failed." 
           --#ARGUMENTS {1,2}
           --#SEVERITY MAJOR
           --#TIMEINDEX 3
           --#STATE DEGRADED
           ::= 180

sysdevBgInitCompleted    TRAP-TYPE
    ENTERPRISE  eMylexRaidEventInformation
    VARIABLES   {
	a9EventCode,
	a9ControllerNumber,
	a9LogicalDriveNumber,
	a9EventTimeStamp
    }
          DESCRIPTION
           "Logical drive background initialization completed."
           --#SUMMARY  "[ctl: %d logdrv: %d :] Logical drive background initialization completed." 
           --#ARGUMENTS {1,2}
           --#SEVERITY INFORMATIONAL
           --#TIMEINDEX 3
           --#STATE OPERATIONAL
           ::= 181

sysdevDataLossLowBbuCharge    TRAP-TYPE
    ENTERPRISE  eMylexRaidEventInformation
    VARIABLES   {
	a9EventCode,
	a9ControllerNumber,
	a9LogicalDriveNumber,
	a9EventTimeStamp
    }
          DESCRIPTION
           "Low battery charge level. Logical drive may have lost data."
           --#SUMMARY  "[ctl: %d logdrv: %d :] Low battery charge level. Logical drive may have lost data." 
           --#ARGUMENTS {1,2}
           --#SEVERITY MAJOR
           --#TIMEINDEX 3
           --#STATE DEGRADED
           ::= 182

sysdevCheckConsMismatch    TRAP-TYPE
    ENTERPRISE  eMylexRaidEventInformation
    VARIABLES   {
	a9EventCode,
	a9ControllerNumber,
	a9LogicalDriveNumber,
	a9EventTimeStamp
    }
          DESCRIPTION
           "Inconsistent data found during consistency check."
           --#SUMMARY  "[ctl: %d logdrv: %d :] Inconsistent data found during consistency check." 
           --#ARGUMENTS {1,2}
           --#SEVERITY MAJOR
           --#TIMEINDEX 3
           --#STATE DEGRADED
           ::= 183

sysdevClusterChange    TRAP-TYPE
    ENTERPRISE  eMylexRaidEventInformation
    VARIABLES   {
	a9EventCode,
	a9ControllerNumber,
	a9LogicalDriveNumber,
	a9EventTimeStamp
    }
          DESCRIPTION
           "Cluster Ownership changed."
           --#SUMMARY  "[ctl: %d logdrv: %d :] Cluster Ownership changed." 
           --#ARGUMENTS {1,2}
           --#SEVERITY INFORMATIONAL
           --#TIMEINDEX 3
           --#STATE OPERATIONAL
           ::= 184

sysdevBginitError    TRAP-TYPE
    ENTERPRISE  eMylexRaidEventInformation
    VARIABLES   {
	a9EventCode,
	a9ControllerNumber,
	a9LogicalDriveNumber,
	a9EventTimeStamp
    }
          DESCRIPTION
           "Unable to recover medium error during background initialization."
           --#SUMMARY  "[ctl: %d logdrv: %d :] Unable to recover medium error during background initialization." 
           --#ARGUMENTS {1,2}
           --#SEVERITY INFORMATIONAL
           --#TIMEINDEX 3
           --#STATE OPERATIONAL
           ::= 185

fmtfanFailed    TRAP-TYPE
    ENTERPRISE  eMylexRaidEventInformation
    VARIABLES   {
	a9EventCode,
	a9ControllerNumber,
	a9FmtCabinetNumber,
	a9EnclosureUnitNumber,
	a9EventTimeStamp
    }
          DESCRIPTION
           "Fan failure."
           --#SUMMARY  "[ctl: %d enclosure: %d unit: %d :] Fan failure." 
           --#ARGUMENTS {1,2,3}
           --#SEVERITY MAJOR
           --#TIMEINDEX 4
           --#STATE DEGRADED
           ::= 256

fmtfanOk    TRAP-TYPE
    ENTERPRISE  eMylexRaidEventInformation
    VARIABLES   {
	a9EventCode,
	a9ControllerNumber,
	a9FmtCabinetNumber,
	a9EnclosureUnitNumber,
	a9EventTimeStamp
    }
          DESCRIPTION
           "Fan has been restored."
           --#SUMMARY  "[ctl: %d enclosure: %d unit: %d :] Fan has been restored." 
           --#ARGUMENTS {1,2,3}
           --#SEVERITY INFORMATIONAL
           --#TIMEINDEX 4
           --#STATE OPERATIONAL
           ::= 257

aemiFanFailed    TRAP-TYPE
    ENTERPRISE  eMylexRaidEventInformation
    VARIABLES   {
	a9EventCode,
	a9ControllerNumber,
	a9ChannelNumber,
	a9TargetNumber,
	a9FanUnitNumber,
	a9EventTimeStamp
    }
          DESCRIPTION
           "Fan failure."
           --#SUMMARY  "[ctl: %d chn: %d tgt: %d Fan: %d :] Fan failure." 
           --#ARGUMENTS {1,2,3,4}
           --#SEVERITY MAJOR
           --#TIMEINDEX 5
           --#STATE DEGRADED
           ::= 258

fmtfanNotpresent    TRAP-TYPE
    ENTERPRISE  eMylexRaidEventInformation
    VARIABLES   {
	a9EventCode,
	a9ControllerNumber,
	a9FmtCabinetNumber,
	a9EventTimeStamp
    }
          DESCRIPTION
           "Storage cabinet fan is not present."
           --#SUMMARY  "[ctl: %d enclosure: %d :] Storage cabinet fan is not present." 
           --#ARGUMENTS {1,2}
           --#SEVERITY INFORMATIONAL
           --#TIMEINDEX 3
           --#STATE OPERATIONAL
           ::= 259

fmtpowerFailed    TRAP-TYPE
    ENTERPRISE  eMylexRaidEventInformation
    VARIABLES   {
	a9EventCode,
	a9ControllerNumber,
	a9FmtCabinetNumber,
	a9EnclosureUnitNumber,
	a9EventTimeStamp
    }
          DESCRIPTION
           "Power supply failure."
           --#SUMMARY  "[ctl: %d enclosure: %d unit: %d :] Power supply failure." 
           --#ARGUMENTS {1,2,3}
           --#SEVERITY MAJOR
           --#TIMEINDEX 4
           --#STATE DEGRADED
           ::= 272

fmtpowerOk    TRAP-TYPE
    ENTERPRISE  eMylexRaidEventInformation
    VARIABLES   {
	a9EventCode,
	a9ControllerNumber,
	a9FmtCabinetNumber,
	a9EnclosureUnitNumber,
	a9EventTimeStamp
    }
          DESCRIPTION
           "Power supply has been restored."
           --#SUMMARY  "[ctl: %d enclosure: %d unit: %d :] Power supply has been restored." 
           --#ARGUMENTS {1,2,3}
           --#SEVERITY INFORMATIONAL
           --#TIMEINDEX 4
           --#STATE OPERATIONAL
           ::= 273

aemiPwrSupplyFailed    TRAP-TYPE
    ENTERPRISE  eMylexRaidEventInformation
    VARIABLES   {
	a9EventCode,
	a9ControllerNumber,
	a9ChannelNumber,
	a9TargetNumber,
	a9PowerSupplyUnitNumber,
	a9EventTimeStamp
    }
          DESCRIPTION
           "Power supply failure."
           --#SUMMARY  "[ctl: %d chn: %d tgt: %d Power Supply: %d :] Power supply failure." 
           --#ARGUMENTS {1,2,3,4}
           --#SEVERITY MAJOR
           --#TIMEINDEX 5
           --#STATE DEGRADED
           ::= 274

fmtpowerNotpresent    TRAP-TYPE
    ENTERPRISE  eMylexRaidEventInformation
    VARIABLES   {
	a9EventCode,
	a9ControllerNumber,
	a9FmtCabinetNumber,
	a9EventTimeStamp
    }
          DESCRIPTION
           "Storage cabinet power supply is not present."
           --#SUMMARY  "[ctl: %d enclosure: %d :] Storage cabinet power supply is not present." 
           --#ARGUMENTS {1,2}
           --#SEVERITY INFORMATIONAL
           --#TIMEINDEX 3
           --#STATE OPERATIONAL
           ::= 275

fmtheatBad    TRAP-TYPE
    ENTERPRISE  eMylexRaidEventInformation
    VARIABLES   {
	a9EventCode,
	a9ControllerNumber,
	a9ChannelNumber,
	a9TargetNumber,
	a9HeatSensorUnitNumber,
	a9EventTimeStamp
    }
          DESCRIPTION
           "Over temperature. Temperature is above 70 degrees Celsius."
           --#SUMMARY  "[ctl: %d chn: %d tgt: %d Heat Sensor: %d :] Over temperature. Temperature is above 70 degrees Celsius." 
           --#ARGUMENTS {1,2,3,4}
           --#SEVERITY MAJOR
           --#TIMEINDEX 5
           --#STATE DEGRADED
           ::= 288

fmtheatCritical    TRAP-TYPE
    ENTERPRISE  eMylexRaidEventInformation
    VARIABLES   {
	a9EventCode,
	a9ControllerNumber,
	a9FmtCabinetNumber,
	a9EnclosureUnitNumber,
	a9EventTimeStamp
    }
          DESCRIPTION
           "Temperature is above 50 degrees Celsius."
           --#SUMMARY  "[ctl: %d enclosure: %d unit: %d :] Temperature is above 50 degrees Celsius." 
           --#ARGUMENTS {1,2,3}
           --#SEVERITY MINOR
           --#TIMEINDEX 4
           --#STATE OPERATIONAL
           ::= 289

fmtheatOk    TRAP-TYPE
    ENTERPRISE  eMylexRaidEventInformation
    VARIABLES   {
	a9EventCode,
	a9ControllerNumber,
	a9FmtCabinetNumber,
	a9EnclosureUnitNumber,
	a9EventTimeStamp
    }
          DESCRIPTION
           "Normal temperature has been restored."
           --#SUMMARY  "[ctl: %d enclosure: %d unit: %d :] Normal temperature has been restored." 
           --#ARGUMENTS {1,2,3}
           --#SEVERITY INFORMATIONAL
           --#TIMEINDEX 4
           --#STATE OPERATIONAL
           ::= 290

aemiOverTemperature    TRAP-TYPE
    ENTERPRISE  eMylexRaidEventInformation
    VARIABLES   {
	a9EventCode,
	a9ControllerNumber,
	a9ChannelNumber,
	a9TargetNumber,
	a9HeatSensorUnitNumber,
	a9EventTimeStamp
    }
          DESCRIPTION
           "Over temperature."
           --#SUMMARY  "[ctl: %d chn: %d tgt: %d Heat Sensor: %d :] Over temperature." 
           --#ARGUMENTS {1,2,3,4}
           --#SEVERITY MAJOR
           --#TIMEINDEX 5
           --#STATE DEGRADED
           ::= 291

fmtheatNotpresent    TRAP-TYPE
    ENTERPRISE  eMylexRaidEventInformation
    VARIABLES   {
	a9EventCode,
	a9ControllerNumber,
	a9FmtCabinetNumber,
	a9EventTimeStamp
    }
          DESCRIPTION
           "Storage cabinet temperature sensor is not present."
           --#SUMMARY  "[ctl: %d enclosure: %d :] Storage cabinet temperature sensor is not present." 
           --#ARGUMENTS {1,2}
           --#SEVERITY INFORMATIONAL
           --#TIMEINDEX 3
           --#STATE OPERATIONAL
           ::= 292

fmtstwkFailed    TRAP-TYPE
    ENTERPRISE  eMylexRaidEventInformation
    VARIABLES   {
	a9EventCode,
	a9ControllerNumber,
	a9ChannelNumber,
	a9EventTimeStamp
    }
          DESCRIPTION
           "Storage Works enclosure reported failure state."
           --#SUMMARY  "[ctl: %d chn: %d :] Storage Works enclosure reported failure state." 
           --#ARGUMENTS {1,2}
           --#SEVERITY MAJOR
           --#TIMEINDEX 3
           --#STATE DEGRADED
           ::= 304

fmtstwkCritical    TRAP-TYPE
    ENTERPRISE  eMylexRaidEventInformation
    VARIABLES   {
	a9EventCode,
	a9ControllerNumber,
	a9ChannelNumber,
	a9EventTimeStamp
    }
          DESCRIPTION
           "Storage Works enclosure reported critical state."
           --#SUMMARY  "[ctl: %d chn: %d :] Storage Works enclosure reported critical state." 
           --#ARGUMENTS {1,2}
           --#SEVERITY MAJOR
           --#TIMEINDEX 3
           --#STATE DEGRADED
           ::= 305

fmtstwkOk    TRAP-TYPE
    ENTERPRISE  eMylexRaidEventInformation
    VARIABLES   {
	a9EventCode,
	a9ControllerNumber,
	a9ChannelNumber,
	a9EventTimeStamp
    }
          DESCRIPTION
           "Storage Works enclosure reported normal state."
           --#SUMMARY  "[ctl: %d chn: %d :] Storage Works enclosure reported normal state." 
           --#ARGUMENTS {1,2}
           --#SEVERITY INFORMATIONAL
           --#TIMEINDEX 3
           --#STATE OPERATIONAL
           ::= 306

fmtUpsDisabled    TRAP-TYPE
    ENTERPRISE  eMylexRaidEventInformation
    VARIABLES   {
	a9EventCode,
	a9ControllerNumber,
	a9EventTimeStamp
    }
          DESCRIPTION
           "Uninterruptible power supply disabled."
           --#SUMMARY  "[ctl: %d :] Uninterruptible power supply disabled." 
           --#ARGUMENTS {1}
           --#SEVERITY INFORMATIONAL
           --#TIMEINDEX 2
           --#STATE OPERATIONAL
           ::= 307

fmtUpsAcFail    TRAP-TYPE
    ENTERPRISE  eMylexRaidEventInformation
    VARIABLES   {
	a9EventCode,
	a9ControllerNumber,
	a9EventTimeStamp
    }
          DESCRIPTION
           "Uninterruptible power supply ac failed."
           --#SUMMARY  "[ctl: %d :] Uninterruptible power supply ac failed." 
           --#ARGUMENTS {1}
           --#SEVERITY INFORMATIONAL
           --#TIMEINDEX 2
           --#STATE OPERATIONAL
           ::= 308

fmtUpsBatLow    TRAP-TYPE
    ENTERPRISE  eMylexRaidEventInformation
    VARIABLES   {
	a9EventCode,
	a9ControllerNumber,
	a9EventTimeStamp
    }
          DESCRIPTION
           "Uninterruptible power supply battery low."
           --#SUMMARY  "[ctl: %d :] Uninterruptible power supply battery low." 
           --#ARGUMENTS {1}
           --#SEVERITY MAJOR
           --#TIMEINDEX 2
           --#STATE DEGRADED
           ::= 309

fmtUpsFailed    TRAP-TYPE
    ENTERPRISE  eMylexRaidEventInformation
    VARIABLES   {
	a9EventCode,
	a9ControllerNumber,
	a9EventTimeStamp
    }
          DESCRIPTION
           "Uninterruptible power supply failed."
           --#SUMMARY  "[ctl: %d :] Uninterruptible power supply failed." 
           --#ARGUMENTS {1}
           --#SEVERITY MAJOR
           --#TIMEINDEX 2
           --#STATE DEGRADED
           ::= 310

fmtUpsOk    TRAP-TYPE
    ENTERPRISE  eMylexRaidEventInformation
    VARIABLES   {
	a9EventCode,
	a9ControllerNumber,
	a9EventTimeStamp
    }
          DESCRIPTION
           "Uninterruptible power supply normal."
           --#SUMMARY  "[ctl: %d :] Uninterruptible power supply normal." 
           --#ARGUMENTS {1}
           --#SEVERITY INFORMATIONAL
           --#TIMEINDEX 2
           --#STATE OPERATIONAL
           ::= 311

enclfanFailed    TRAP-TYPE
    ENTERPRISE  eMylexRaidEventInformation
    VARIABLES   {
	a9EventCode,
	a9ControllerNumber,
	a9FmtCabinetNumber,
	a9EnclosureUnitNumber,
	a9EventTimeStamp
    }
          DESCRIPTION
           "Fan failure."
           --#SUMMARY  "[ctl: %d enclosure: %d unit: %d :] Fan failure." 
           --#ARGUMENTS {1,2,3}
           --#SEVERITY MAJOR
           --#TIMEINDEX 4
           --#STATE DEGRADED
           ::= 320

enclfanOk    TRAP-TYPE
    ENTERPRISE  eMylexRaidEventInformation
    VARIABLES   {
	a9EventCode,
	a9ControllerNumber,
	a9FmtCabinetNumber,
	a9EnclosureUnitNumber,
	a9EventTimeStamp
    }
          DESCRIPTION
           "Fan has been restored."
           --#SUMMARY  "[ctl: %d enclosure: %d unit: %d :] Fan has been restored." 
           --#ARGUMENTS {1,2,3}
           --#SEVERITY INFORMATIONAL
           --#TIMEINDEX 4
           --#STATE OPERATIONAL
           ::= 321

enclfanNotpresent    TRAP-TYPE
    ENTERPRISE  eMylexRaidEventInformation
    VARIABLES   {
	a9EventCode,
	a9ControllerNumber,
	a9FmtCabinetNumber,
	a9EnclosureUnitNumber,
	a9EventTimeStamp
    }
          DESCRIPTION
           "Fan is not present."
           --#SUMMARY  "[ctl: %d enclosure: %d unit: %d :] Fan is not present." 
           --#ARGUMENTS {1,2,3}
           --#SEVERITY INFORMATIONAL
           --#TIMEINDEX 4
           --#STATE OPERATIONAL
           ::= 322

enclpowerFailed    TRAP-TYPE
    ENTERPRISE  eMylexRaidEventInformation
    VARIABLES   {
	a9EventCode,
	a9ControllerNumber,
	a9FmtCabinetNumber,
	a9EnclosureUnitNumber,
	a9EventTimeStamp
    }
          DESCRIPTION
           "Power supply failure."
           --#SUMMARY  "[ctl: %d enclosure: %d unit: %d :] Power supply failure." 
           --#ARGUMENTS {1,2,3}
           --#SEVERITY MAJOR
           --#TIMEINDEX 4
           --#STATE DEGRADED
           ::= 323

enclpowerOk    TRAP-TYPE
    ENTERPRISE  eMylexRaidEventInformation
    VARIABLES   {
	a9EventCode,
	a9ControllerNumber,
	a9FmtCabinetNumber,
	a9EnclosureUnitNumber,
	a9EventTimeStamp
    }
          DESCRIPTION
           "Power supply has been restored."
           --#SUMMARY  "[ctl: %d enclosure: %d unit: %d :] Power supply has been restored." 
           --#ARGUMENTS {1,2,3}
           --#SEVERITY INFORMATIONAL
           --#TIMEINDEX 4
           --#STATE OPERATIONAL
           ::= 324

enclpowerNotpresent    TRAP-TYPE
    ENTERPRISE  eMylexRaidEventInformation
    VARIABLES   {
	a9EventCode,
	a9ControllerNumber,
	a9FmtCabinetNumber,
	a9EnclosureUnitNumber,
	a9EventTimeStamp
    }
          DESCRIPTION
           "Power supply is not present."
           --#SUMMARY  "[ctl: %d enclosure: %d unit: %d :] Power supply is not present." 
           --#ARGUMENTS {1,2,3}
           --#SEVERITY INFORMATIONAL
           --#TIMEINDEX 4
           --#STATE OPERATIONAL
           ::= 325

enclheatBad    TRAP-TYPE
    ENTERPRISE  eMylexRaidEventInformation
    VARIABLES   {
	a9EventCode,
	a9ControllerNumber,
	a9FmtCabinetNumber,
	a9EnclosureUnitNumber,
	a9EventTimeStamp
    }
          DESCRIPTION
           "Temperature is over safe limit. Failure imminent."
           --#SUMMARY  "[ctl: %d enclosure: %d unit: %d :] Temperature is over safe limit. Failure imminent." 
           --#ARGUMENTS {1,2,3}
           --#SEVERITY MAJOR
           --#TIMEINDEX 4
           --#STATE DEGRADED
           ::= 326

enclheatCritical    TRAP-TYPE
    ENTERPRISE  eMylexRaidEventInformation
    VARIABLES   {
	a9EventCode,
	a9ControllerNumber,
	a9FmtCabinetNumber,
	a9EnclosureUnitNumber,
	a9EventTimeStamp
    }
          DESCRIPTION
           "Temperature is above working limit."
           --#SUMMARY  "[ctl: %d enclosure: %d unit: %d :] Temperature is above working limit." 
           --#ARGUMENTS {1,2,3}
           --#SEVERITY MAJOR
           --#TIMEINDEX 4
           --#STATE DEGRADED
           ::= 327

enclheatOk    TRAP-TYPE
    ENTERPRISE  eMylexRaidEventInformation
    VARIABLES   {
	a9EventCode,
	a9ControllerNumber,
	a9FmtCabinetNumber,
	a9EnclosureUnitNumber,
	a9EventTimeStamp
    }
          DESCRIPTION
           "Normal temperature has been restored."
           --#SUMMARY  "[ctl: %d enclosure: %d unit: %d :] Normal temperature has been restored." 
           --#ARGUMENTS {1,2,3}
           --#SEVERITY INFORMATIONAL
           --#TIMEINDEX 4
           --#STATE OPERATIONAL
           ::= 328

enclheatNotpresent    TRAP-TYPE
    ENTERPRISE  eMylexRaidEventInformation
    VARIABLES   {
	a9EventCode,
	a9ControllerNumber,
	a9FmtCabinetNumber,
	a9EnclosureUnitNumber,
	a9EventTimeStamp
    }
          DESCRIPTION
           "Temperature sensor is not present."
           --#SUMMARY  "[ctl: %d enclosure: %d unit: %d :] Temperature sensor is not present." 
           --#ARGUMENTS {1,2,3}
           --#SEVERITY INFORMATIONAL
           --#TIMEINDEX 4
           --#STATE OPERATIONAL
           ::= 329

enclaccessCritical    TRAP-TYPE
    ENTERPRISE  eMylexRaidEventInformation
    VARIABLES   {
	a9EventCode,
	a9ControllerNumber,
	a9FmtCabinetNumber,
	a9EventTimeStamp
    }
          DESCRIPTION
           "Enclosure access critical."
           --#SUMMARY  "[ctl: %d enclosure: %d :] Enclosure access critical." 
           --#ARGUMENTS {1,2}
           --#SEVERITY MAJOR
           --#TIMEINDEX 3
           --#STATE DEGRADED
           ::= 330

enclaccessOk    TRAP-TYPE
    ENTERPRISE  eMylexRaidEventInformation
    VARIABLES   {
	a9EventCode,
	a9ControllerNumber,
	a9FmtCabinetNumber,
	a9EventTimeStamp
    }
          DESCRIPTION
           "Enclosure access has been restored."
           --#SUMMARY  "[ctl: %d enclosure: %d :] Enclosure access has been restored." 
           --#ARGUMENTS {1,2}
           --#SEVERITY INFORMATIONAL
           --#TIMEINDEX 3
           --#STATE OPERATIONAL
           ::= 331

enclaccessOffline    TRAP-TYPE
    ENTERPRISE  eMylexRaidEventInformation
    VARIABLES   {
	a9EventCode,
	a9ControllerNumber,
	a9FmtCabinetNumber,
	a9EventTimeStamp
    }
          DESCRIPTION
           "Enclosure access is offline."
           --#SUMMARY  "[ctl: %d enclosure: %d :] Enclosure access is offline." 
           --#ARGUMENTS {1,2}
           --#SEVERITY MAJOR
           --#TIMEINDEX 3
           --#STATE DEGRADED
           ::= 332

enclsesSoftaddrOccurred    TRAP-TYPE
    ENTERPRISE  eMylexRaidEventInformation
    VARIABLES   {
	a9EventCode,
	a9ControllerNumber,
	a9FmtCabinetNumber,
	a9EventTimeStamp
    }
          DESCRIPTION
           "Enclosure soft addressing detected."
           --#SUMMARY  "[ctl: %d enclosure: %d :] Enclosure soft addressing detected." 
           --#ARGUMENTS {1,2}
           --#SEVERITY MAJOR
           --#TIMEINDEX 3
           --#STATE DEGRADED
           ::= 333

enclaccessReady    TRAP-TYPE
    ENTERPRISE  eMylexRaidEventInformation
    VARIABLES   {
	a9EventCode,
	a9ControllerNumber,
	a9EventTimeStamp
    }
          DESCRIPTION
           "Enclosure services ready."
           --#SUMMARY  "[ctl: %d :] Enclosure services ready." 
           --#ARGUMENTS {1}
           --#SEVERITY INFORMATIONAL
           --#TIMEINDEX 2
           --#STATE OPERATIONAL
           ::= 334

enclheatUnknown    TRAP-TYPE
    ENTERPRISE  eMylexRaidEventInformation
    VARIABLES   {
	a9EventCode,
	a9ControllerNumber,
	a9FmtCabinetNumber,
	a9EnclosureUnitNumber,
	a9EventTimeStamp
    }
          DESCRIPTION
           "Access to temperature sensor has been lost."
           --#SUMMARY  "[ctl: %d enclosure: %d unit: %d :] Access to temperature sensor has been lost." 
           --#ARGUMENTS {1,2,3}
           --#SEVERITY INFORMATIONAL
           --#TIMEINDEX 4
           --#STATE OPERATIONAL
           ::= 335

enclpowerUnknown    TRAP-TYPE
    ENTERPRISE  eMylexRaidEventInformation
    VARIABLES   {
	a9EventCode,
	a9ControllerNumber,
	a9FmtCabinetNumber,
	a9EnclosureUnitNumber,
	a9EventTimeStamp
    }
          DESCRIPTION
           "Access to power supply status information has been lost."
           --#SUMMARY  "[ctl: %d enclosure: %d unit: %d :] Access to power supply status information has been lost." 
           --#ARGUMENTS {1,2,3}
           --#SEVERITY INFORMATIONAL
           --#TIMEINDEX 4
           --#STATE OPERATIONAL
           ::= 336

enclfanUnknown    TRAP-TYPE
    ENTERPRISE  eMylexRaidEventInformation
    VARIABLES   {
	a9EventCode,
	a9ControllerNumber,
	a9FmtCabinetNumber,
	a9EnclosureUnitNumber,
	a9EventTimeStamp
    }
          DESCRIPTION
           "Access to fan status information has been lost."
           --#SUMMARY  "[ctl: %d enclosure: %d unit: %d :] Access to fan status information has been lost." 
           --#ARGUMENTS {1,2,3}
           --#SEVERITY INFORMATIONAL
           --#TIMEINDEX 4
           --#STATE OPERATIONAL
           ::= 337

enclosureShutdown    TRAP-TYPE
    ENTERPRISE  eMylexRaidEventInformation
    VARIABLES   {
	a9EventCode,
	a9ControllerNumber,
	a9FmtCabinetNumber,
	a9EnclosureUnitNumber,
	a9EventTimeStamp
    }
          DESCRIPTION
           "Physical disks in enclosure being spundown."
           --#SUMMARY  "[ctl: %d enclosure: %d unit: %d :] Physical disks in enclosure being spundown." 
           --#ARGUMENTS {1,2,3}
           --#SEVERITY MAJOR
           --#TIMEINDEX 4
           --#STATE DEGRADED
           ::= 338

enclcoldWarn    TRAP-TYPE
    ENTERPRISE  eMylexRaidEventInformation
    VARIABLES   {
	a9EventCode,
	a9ControllerNumber,
	a9FmtCabinetNumber,
	a9EventTimeStamp
    }
          DESCRIPTION
           "Temperature is below working limit."
           --#SUMMARY  "[ctl: %d enclosure: %d :] Temperature is below working limit." 
           --#ARGUMENTS {1,2}
           --#SEVERITY MAJOR
           --#TIMEINDEX 3
           --#STATE DEGRADED
           ::= 339

enclcoldFail    TRAP-TYPE
    ENTERPRISE  eMylexRaidEventInformation
    VARIABLES   {
	a9EventCode,
	a9ControllerNumber,
	a9FmtCabinetNumber,
	a9EventTimeStamp
    }
          DESCRIPTION
           "Temperature is under safe limit. Failure imminent."
           --#SUMMARY  "[ctl: %d enclosure: %d :] Temperature is under safe limit. Failure imminent." 
           --#ARGUMENTS {1,2}
           --#SEVERITY MAJOR
           --#TIMEINDEX 3
           --#STATE DEGRADED
           ::= 340

enclSesDiscovered    TRAP-TYPE
    ENTERPRISE  eMylexRaidEventInformation
    VARIABLES   {
	a9EventCode,
	a9ControllerNumber,
	a9FmtCabinetNumber,
	a9EventTimeStamp
    }
          DESCRIPTION
           "Enclosure (SES) discovered."
           --#SUMMARY  "[ctl: %d enclosure: %d :] Enclosure (SES) discovered." 
           --#ARGUMENTS {1,2}
           --#SEVERITY INFORMATIONAL
           --#TIMEINDEX 3
           --#STATE DEGRADED
           ::= 341

enclSafteDiscovered    TRAP-TYPE
    ENTERPRISE  eMylexRaidEventInformation
    VARIABLES   {
	a9EventCode,
	a9ControllerNumber,
	a9FmtCabinetNumber,
	a9EventTimeStamp
    }
          DESCRIPTION
           "Enclosure (SAF-TE) discovered."
           --#SUMMARY  "[ctl: %d enclosure: %d :] Enclosure (SAF-TE) discovered." 
           --#ARGUMENTS {1,2}
           --#SEVERITY INFORMATIONAL
           --#TIMEINDEX 3
           --#STATE DEGRADED
           ::= 342

enclSimFailed    TRAP-TYPE
    ENTERPRISE  eMylexRaidEventInformation
    VARIABLES   {
	a9EventCode,
	a9ControllerNumber,
	a9FmtCabinetNumber,
	a9EnclosureUnitNumber,
	a9EventTimeStamp
    }
          DESCRIPTION
           "SIM failure."
           --#SUMMARY  "[ctl: %d enclosure: %d unit: %d :] SIM failure." 
           --#ARGUMENTS {1,2,3}
           --#SEVERITY MAJOR
           --#TIMEINDEX 4
           --#STATE OPERATIONAL
           ::= 343

enclSimOk    TRAP-TYPE
    ENTERPRISE  eMylexRaidEventInformation
    VARIABLES   {
	a9EventCode,
	a9ControllerNumber,
	a9FmtCabinetNumber,
	a9EnclosureUnitNumber,
	a9EventTimeStamp
    }
          DESCRIPTION
           "SIM has been restored."
           --#SUMMARY  "[ctl: %d enclosure: %d unit: %d :] SIM has been restored." 
           --#ARGUMENTS {1,2,3}
           --#SEVERITY INFORMATIONAL
           --#TIMEINDEX 4
           --#STATE OPERATIONAL
           ::= 344

enclSimNotPresent    TRAP-TYPE
    ENTERPRISE  eMylexRaidEventInformation
    VARIABLES   {
	a9EventCode,
	a9ControllerNumber,
	a9FmtCabinetNumber,
	a9EnclosureUnitNumber,
	a9EventTimeStamp
    }
          DESCRIPTION
           "SIM is not present."
           --#SUMMARY  "[ctl: %d enclosure: %d unit: %d :] SIM is not present." 
           --#ARGUMENTS {1,2,3}
           --#SEVERITY INFORMATIONAL
           --#TIMEINDEX 4
           --#STATE OPERATIONAL
           ::= 345

enclmaxPerPortExceed    TRAP-TYPE
    ENTERPRISE  eMylexRaidEventInformation
    VARIABLES   {
	a9EventCode,
	a9ControllerNumber,
	a9FmtCabinetNumber,
	a9EventTimeStamp
    }
          DESCRIPTION
           "Enclosure not supported; too many enclosures connected to port."
           --#SUMMARY  "[ctl: %d enclosure: %d :] Enclosure not supported; too many enclosures connected to port." 
           --#ARGUMENTS {1,2}
           --#SEVERITY MAJOR
           --#TIMEINDEX 3
           --#STATE DEGRADED
           ::= 346

enclFirmwareMismatch    TRAP-TYPE
    ENTERPRISE  eMylexRaidEventInformation
    VARIABLES   {
	a9EventCode,
	a9ControllerNumber,
	a9FmtCabinetNumber,
	a9EventTimeStamp
    }
          DESCRIPTION
           "Enclosure firmware mismatch."
           --#SUMMARY  "[ctl: %d enclosure: %d :] Enclosure firmware mismatch." 
           --#ARGUMENTS {1,2}
           --#SEVERITY MAJOR
           --#TIMEINDEX 3
           --#STATE DEGRADED
           ::= 347

enclSensorBad    TRAP-TYPE
    ENTERPRISE  eMylexRaidEventInformation
    VARIABLES   {
	a9EventCode,
	a9ControllerNumber,
	a9FmtCabinetNumber,
	a9EnclosureUnitNumber,
	a9EventTimeStamp
    }
          DESCRIPTION
           "Sensor bad."
           --#SUMMARY  "[ctl: %d enclosure: %d unit: %d :] Sensor bad." 
           --#ARGUMENTS {1,2,3}
           --#SEVERITY MAJOR
           --#TIMEINDEX 4
           --#STATE OPERATIONAL
           ::= 348

enclPhyBad    TRAP-TYPE
    ENTERPRISE  eMylexRaidEventInformation
    VARIABLES   {
	a9EventCode,
	a9ControllerNumber,
	a9FmtCabinetNumber,
	a9EnclosureUnitNumber,
	a9EventTimeStamp
    }
          DESCRIPTION
           "Enclosure phy bad."
           --#SUMMARY  "[ctl: %d enclosure: %d unit: %d :] Enclosure phy bad." 
           --#ARGUMENTS {1,2,3}
           --#SEVERITY MAJOR
           --#TIMEINDEX 4
           --#STATE OPERATIONAL
           ::= 349

enclSasSataMixingDetected    TRAP-TYPE
    ENTERPRISE  eMylexRaidEventInformation
    VARIABLES   {
	a9EventCode,
	a9ControllerNumber,
	a9ChannelNumber,
	a9TargetNumber,
	a9EventTimeStamp
    }
          DESCRIPTION
           "SAS/SATA mixing not supported in enclosure; PD disabled."
           --#SUMMARY  "[ctl: %d chn: %d tgt: %d :] SAS/SATA mixing not supported in enclosure; PD disabled." 
           --#ARGUMENTS {1,2,3}
           --#SEVERITY MAJOR
           --#TIMEINDEX 4
           --#STATE OPERATIONAL
           ::= 350

enclSesHotplugDetected    TRAP-TYPE
    ENTERPRISE  eMylexRaidEventInformation
    VARIABLES   {
	a9EventCode,
	a9ControllerNumber,
	a9ChannelNumber,
	a9TargetNumber,
	a9EventTimeStamp
    }
          DESCRIPTION
           "Enclosure (SES) hotplug on was detected, but is not supported."
           --#SUMMARY  "[ctl: %d chn: %d tgt: %d :] Enclosure (SES) hotplug on was detected, but is not supported." 
           --#ARGUMENTS {1,2,3}
           --#SEVERITY MINOR
           --#TIMEINDEX 4
           --#STATE OPERATIONAL
           ::= 351

enclPowerSupplyOff    TRAP-TYPE
    ENTERPRISE  eMylexRaidEventInformation
    VARIABLES   {
	a9EventCode,
	a9ControllerNumber,
	a9FmtCabinetNumber,
	a9EnclosureUnitNumber,
	a9EventTimeStamp
    }
          DESCRIPTION
           "Enclosure power supply has been turned off."
           --#SUMMARY  "[ctl: %d enclosure: %d unit: %d :] Enclosure power supply has been turned off." 
           --#ARGUMENTS {1,2,3}
           --#SEVERITY INFORMATIONAL
           --#TIMEINDEX 4
           --#STATE OPERATIONAL
           ::= 352

enclPowerSupplyOn    TRAP-TYPE
    ENTERPRISE  eMylexRaidEventInformation
    VARIABLES   {
	a9EventCode,
	a9ControllerNumber,
	a9FmtCabinetNumber,
	a9EnclosureUnitNumber,
	a9EventTimeStamp
    }
          DESCRIPTION
           "Enclosure power supply has been turned on."
           --#SUMMARY  "[ctl: %d enclosure: %d unit: %d :] Enclosure power supply has been turned on." 
           --#ARGUMENTS {1,2,3}
           --#SEVERITY INFORMATIONAL
           --#TIMEINDEX 4
           --#STATE OPERATIONAL
           ::= 353

enclPowerSupplyCableRemoved    TRAP-TYPE
    ENTERPRISE  eMylexRaidEventInformation
    VARIABLES   {
	a9EventCode,
	a9ControllerNumber,
	a9FmtCabinetNumber,
	a9EnclosureUnitNumber,
	a9EventTimeStamp
    }
          DESCRIPTION
           "Enclosure power supply cable has been removed."
           --#SUMMARY  "[ctl: %d enclosure: %d unit: %d :] Enclosure power supply cable has been removed." 
           --#ARGUMENTS {1,2,3}
           --#SEVERITY INFORMATIONAL
           --#TIMEINDEX 4
           --#STATE OPERATIONAL
           ::= 354

enclPowerSupplyCableInserted    TRAP-TYPE
    ENTERPRISE  eMylexRaidEventInformation
    VARIABLES   {
	a9EventCode,
	a9ControllerNumber,
	a9FmtCabinetNumber,
	a9EnclosureUnitNumber,
	a9EventTimeStamp
    }
          DESCRIPTION
           "Enclosure power supply cable has been inserted."
           --#SUMMARY  "[ctl: %d enclosure: %d unit: %d :] Enclosure power supply cable has been inserted." 
           --#ARGUMENTS {1,2,3}
           --#SEVERITY INFORMATIONAL
           --#TIMEINDEX 4
           --#STATE OPERATIONAL
           ::= 355

enclFanReturnedToNormal    TRAP-TYPE
    ENTERPRISE  eMylexRaidEventInformation
    VARIABLES   {
	a9EventCode,
	a9ControllerNumber,
	a9FmtCabinetNumber,
	a9EnclosureUnitNumber,
	a9EventTimeStamp
    }
          DESCRIPTION
           "Enclosure fan returned to normal."
           --#SUMMARY  "[ctl: %d enclosure: %d unit: %d :] Enclosure fan returned to normal." 
           --#ARGUMENTS {1,2,3}
           --#SEVERITY INFORMATIONAL
           --#TIMEINDEX 4
           --#STATE OPERATIONAL
           ::= 356

enclTempDifferential    TRAP-TYPE
    ENTERPRISE  eMylexRaidEventInformation
    VARIABLES   {
	a9EventCode,
	a9ControllerNumber,
	a9FmtCabinetNumber,
	a9EnclosureUnitNumber,
	a9EventTimeStamp
    }
          DESCRIPTION
           "Enclosure temperature difference has been detected."
           --#SUMMARY  "[ctl: %d enclosure: %d unit: %d :] Enclosure temperature difference has been detected." 
           --#ARGUMENTS {1,2,3}
           --#SEVERITY INFORMATIONAL
           --#TIMEINDEX 4
           --#STATE OPERATIONAL
           ::= 357

ctldevBbuChargeComplete    TRAP-TYPE
    ENTERPRISE  eMylexRaidEventInformation
    VARIABLES   {
	a9EventCode,
	a9ControllerNumber,
	a9EventTimeStamp
    }
          DESCRIPTION
           "Battery charge complete"
           --#SUMMARY  "[ctl: %d :] Battery charge complete." 
           --#ARGUMENTS {1}
           --#SEVERITY INFORMATIONAL
           --#TIMEINDEX 2
           --#STATE OPERATIONAL
           ::= 480

systemStarted    TRAP-TYPE
    ENTERPRISE  eMylexRaidEventInformation
    VARIABLES   {
	a9EventCode,
	a9EventTimeStamp
    }
          DESCRIPTION
           "Array management server software started successfully."
           --#SUMMARY  "    Array management server software started successfully." 
           --#ARGUMENTS {}
           --#SEVERITY INFORMATIONAL
           --#TIMEINDEX 1
           --#STATE OPERATIONAL
           ::= 384

ctldevWritebackError    TRAP-TYPE
    ENTERPRISE  eMylexRaidEventInformation
    VARIABLES   {
	a9EventCode,
	a9ControllerNumber,
	a9EventTimeStamp
    }
          DESCRIPTION
           "Write back error."
           --#SUMMARY  "[ctl: %d :] Write back error." 
           --#ARGUMENTS {1}
           --#SEVERITY MAJOR
           --#TIMEINDEX 2
           --#STATE DEGRADED
           ::= 385

ctldevStateTableFull    TRAP-TYPE
    ENTERPRISE  eMylexRaidEventInformation
    VARIABLES   {
	a9EventCode,
	a9ControllerNumber,
	a9EventTimeStamp
    }
          DESCRIPTION
           "Internal log structures getting full,PLEASE SHUTDOWN AND RESET THE SYSTEM IN THE NEAR FUTURE."
           --#SUMMARY  "[ctl: %d :] Internal log structures getting full,PLEASE SHUTDOWN AND RESET THE SYSTEM IN THE NEAR FUTURE." 
           --#ARGUMENTS {1}
           --#SEVERITY MINOR
           --#TIMEINDEX 2
           --#STATE OPERATIONAL
           ::= 386

ctldevDead    TRAP-TYPE
    ENTERPRISE  eMylexRaidEventInformation
    VARIABLES   {
	a9EventCode,
	a9ControllerNumber,
	a9EventTimeStamp
    }
          DESCRIPTION
           "Controller is dead. System is disconnecting from this controller."
           --#SUMMARY  "[ctl: %d :] Controller is dead. System is disconnecting from this controller." 
           --#ARGUMENTS {1}
           --#SEVERITY CRITICAL
           --#TIMEINDEX 2
           --#STATE NONOPERATIONAL
           ::= 388

ctldevReset    TRAP-TYPE
    ENTERPRISE  eMylexRaidEventInformation
    VARIABLES   {
	a9EventCode,
	a9ControllerNumber,
	a9EventTimeStamp
    }
          DESCRIPTION
           "Controller has been reset."
           --#SUMMARY  "[ctl: %d :] Controller has been reset." 
           --#ARGUMENTS {1}
           --#SEVERITY INFORMATIONAL
           --#TIMEINDEX 2
           --#STATE OPERATIONAL
           ::= 389

ctldevFound    TRAP-TYPE
    ENTERPRISE  eMylexRaidEventInformation
    VARIABLES   {
	a9EventCode,
	a9ControllerNumber,
	a9EventTimeStamp
    }
          DESCRIPTION
           "Controller is found."
           --#SUMMARY  "[ctl: %d :] Controller is found." 
           --#ARGUMENTS {1}
           --#SEVERITY INFORMATIONAL
           --#TIMEINDEX 2
           --#STATE OPERATIONAL
           ::= 390

ctldevGone    TRAP-TYPE
    ENTERPRISE  eMylexRaidEventInformation
    VARIABLES   {
	a9EventCode,
	a9ControllerNumber,
	a9EventTimeStamp
    }
          DESCRIPTION
           "Controller is gone. System is disconnecting from this controller."
           --#SUMMARY  "[ctl: %d :] Controller is gone. System is disconnecting from this controller." 
           --#ARGUMENTS {1}
           --#SEVERITY CRITICAL
           --#TIMEINDEX 2
           --#STATE NONOPERATIONAL
           ::= 391

ctldevBbuFound    TRAP-TYPE
    ENTERPRISE  eMylexRaidEventInformation
    VARIABLES   {
	a9EventCode,
	a9ControllerNumber,
	a9EventTimeStamp
    }
          DESCRIPTION
           "Battery present."
           --#SUMMARY  "[ctl: %d :] Battery present." 
           --#ARGUMENTS {1}
           --#SEVERITY INFORMATIONAL
           --#TIMEINDEX 2
           --#STATE OPERATIONAL
           ::= 392

ctldevBbuPowerLow    TRAP-TYPE
    ENTERPRISE  eMylexRaidEventInformation
    VARIABLES   {
	a9EventCode,
	a9ControllerNumber,
	a9EventTimeStamp
    }
          DESCRIPTION
           "Battery is bad."
           --#SUMMARY  "[ctl: %d :] Battery is bad." 
           --#ARGUMENTS {1}
           --#SEVERITY MAJOR
           --#TIMEINDEX 2
           --#STATE DEGRADED
           ::= 393

ctldevBbuPowerOk    TRAP-TYPE
    ENTERPRISE  eMylexRaidEventInformation
    VARIABLES   {
	a9EventCode,
	a9ControllerNumber,
	a9EventTimeStamp
    }
          DESCRIPTION
           "Battery power OK."
           --#SUMMARY  "[ctl: %d :] Battery power OK." 
           --#ARGUMENTS {1}
           --#SEVERITY INFORMATIONAL
           --#TIMEINDEX 2
           --#STATE OPERATIONAL
           ::= 394

ctldevPowerOff    TRAP-TYPE
    ENTERPRISE  eMylexRaidEventInformation
    VARIABLES   {
	a9EventCode,
	a9ControllerNumber,
	a9EventTimeStamp
    }
          DESCRIPTION
           "Controller is gone. System is disconnecting from this controller."
           --#SUMMARY  "[ctl: %d :] Controller is gone. System is disconnecting from this controller." 
           --#ARGUMENTS {1}
           --#SEVERITY CRITICAL
           --#TIMEINDEX 2
           --#STATE NONOPERATIONAL
           ::= 395

ctldevPowerOn    TRAP-TYPE
    ENTERPRISE  eMylexRaidEventInformation
    VARIABLES   {
	a9EventCode,
	a9ControllerNumber,
	a9EventTimeStamp
    }
          DESCRIPTION
           "Controller powered on"
           --#SUMMARY  "[ctl: %d :] Controller powered on" 
           --#ARGUMENTS {1}
           --#SEVERITY INFORMATIONAL
           --#TIMEINDEX 2
           --#STATE OPERATIONAL
           ::= 396

ctldevOnline    TRAP-TYPE
    ENTERPRISE  eMylexRaidEventInformation
    VARIABLES   {
	a9EventCode,
	a9ControllerNumber,
	a9EventTimeStamp
    }
          DESCRIPTION
           "Controller is online."
           --#SUMMARY  "[ctl: %d :] Controller is online." 
           --#ARGUMENTS {1}
           --#SEVERITY INFORMATIONAL
           --#TIMEINDEX 2
           --#STATE OPERATIONAL
           ::= 397

ctldevOffline    TRAP-TYPE
    ENTERPRISE  eMylexRaidEventInformation
    VARIABLES   {
	a9EventCode,
	a9ControllerNumber,
	a9EventTimeStamp
    }
          DESCRIPTION
           "Controller is gone. System is disconnecting from this controller."
           --#SUMMARY  "[ctl: %d :] Controller is gone. System is disconnecting from this controller." 
           --#ARGUMENTS {1}
           --#SEVERITY CRITICAL
           --#TIMEINDEX 2
           --#STATE NONOPERATIONAL
           ::= 398

ctldevCritical    TRAP-TYPE
    ENTERPRISE  eMylexRaidEventInformation
    VARIABLES   {
	a9EventCode,
	a9ControllerNumber,
	a9EventTimeStamp
    }
          DESCRIPTION
           "Controller's partner is gone, controller is in failover mode now."
           --#SUMMARY  "[ctl: %d :] Controller's partner is gone, controller is in failover mode now." 
           --#ARGUMENTS {1}
           --#SEVERITY MINOR
           --#TIMEINDEX 2
           --#STATE OPERATIONAL
           ::= 399

ctldevBbuRecondStart    TRAP-TYPE
    ENTERPRISE  eMylexRaidEventInformation
    VARIABLES   {
	a9EventCode,
	a9ControllerNumber,
	a9EventTimeStamp
    }
          DESCRIPTION
           "Battery reconditioning is started."
           --#SUMMARY  "[ctl: %d :] Battery reconditioning is started." 
           --#ARGUMENTS {1}
           --#SEVERITY INFORMATIONAL
           --#TIMEINDEX 2
           --#STATE OPERATIONAL
           ::= 400

ctldevBbuRecondDone    TRAP-TYPE
    ENTERPRISE  eMylexRaidEventInformation
    VARIABLES   {
	a9EventCode,
	a9ControllerNumber,
	a9EventTimeStamp
    }
          DESCRIPTION
           "Battery reconditioning is finished."
           --#SUMMARY  "[ctl: %d :] Battery reconditioning is finished." 
           --#ARGUMENTS {1}
           --#SEVERITY INFORMATIONAL
           --#TIMEINDEX 2
           --#STATE OPERATIONAL
           ::= 401

ctldevBbuRecondAbort    TRAP-TYPE
    ENTERPRISE  eMylexRaidEventInformation
    VARIABLES   {
	a9EventCode,
	a9ControllerNumber,
	a9EventTimeStamp
    }
          DESCRIPTION
           "Battery reconditioning is canceled."
           --#SUMMARY  "[ctl: %d :] Battery reconditioning is canceled." 
           --#ARGUMENTS {1}
           --#SEVERITY INFORMATIONAL
           --#TIMEINDEX 2
           --#STATE OPERATIONAL
           ::= 402

ctldevInstallationAborted    TRAP-TYPE
    ENTERPRISE  eMylexRaidEventInformation
    VARIABLES   {
	a9EventCode,
	a9ControllerNumber,
	a9EventTimeStamp
    }
          DESCRIPTION
           "Installation aborted."
           --#SUMMARY  "[ctl: %d :] Installation aborted." 
           --#ARGUMENTS {1}
           --#SEVERITY MAJOR
           --#TIMEINDEX 2
           --#STATE DEGRADED
           ::= 403

ctldevFirmwareMismatch    TRAP-TYPE
    ENTERPRISE  eMylexRaidEventInformation
    VARIABLES   {
	a9EventCode,
	a9ControllerNumber,
	a9ChannelNumber,
	a9TargetNumber,
	a9EventTimeStamp
    }
          DESCRIPTION
           "Controller firmware mismatch."
           --#SUMMARY  "[ctl: %d chn: %d tgt: %d :] Controller firmware mismatch." 
           --#ARGUMENTS {1,2,3}
           --#SEVERITY MAJOR
           --#TIMEINDEX 4
           --#STATE DEGRADED
           ::= 404

ctldevBbuNoresponse    TRAP-TYPE
    ENTERPRISE  eMylexRaidEventInformation
    VARIABLES   {
	a9EventCode,
	a9ControllerNumber,
	a9EventTimeStamp
    }
          DESCRIPTION
           "The Battery Backup Unit is removed."
           --#SUMMARY  "[ctl: %d :] The Battery Backup Unit is removed." 
           --#ARGUMENTS {1}
           --#SEVERITY MAJOR
           --#TIMEINDEX 2
           --#STATE DEGRADED
           ::= 405

ctldevWarmBootError    TRAP-TYPE
    ENTERPRISE  eMylexRaidEventInformation
    VARIABLES   {
	a9EventCode,
	a9ControllerNumber,
	a9EventTimeStamp
    }
          DESCRIPTION
           "WARM BOOT failed."
           --#SUMMARY  "[ctl: %d :] WARM BOOT failed." 
           --#ARGUMENTS {1}
           --#SEVERITY MAJOR
           --#TIMEINDEX 2
           --#STATE DEGRADED
           ::= 406

ctldevBbuCalibrateStart    TRAP-TYPE
    ENTERPRISE  eMylexRaidEventInformation
    VARIABLES   {
	a9EventCode,
	a9ControllerNumber,
	a9EventTimeStamp
    }
          DESCRIPTION
           "Battery calibration cycle started."
           --#SUMMARY  "[ctl: %d :] Battery calibration cycle started." 
           --#ARGUMENTS {1}
           --#SEVERITY INFORMATIONAL
           --#TIMEINDEX 2
           --#STATE OPERATIONAL
           ::= 407

ctldevBbuCalibrateDone    TRAP-TYPE
    ENTERPRISE  eMylexRaidEventInformation
    VARIABLES   {
	a9EventCode,
	a9ControllerNumber,
	a9EventTimeStamp
    }
          DESCRIPTION
           "Battery calibration cycle finished."
           --#SUMMARY  "[ctl: %d :] Battery calibration cycle finished." 
           --#ARGUMENTS {1}
           --#SEVERITY INFORMATIONAL
           --#TIMEINDEX 2
           --#STATE OPERATIONAL
           ::= 408

ctldevBbuCalibrateAbort    TRAP-TYPE
    ENTERPRISE  eMylexRaidEventInformation
    VARIABLES   {
	a9EventCode,
	a9ControllerNumber,
	a9EventTimeStamp
    }
          DESCRIPTION
           "Battery calibration cycle was cancelled."
           --#SUMMARY  "[ctl: %d :] Battery calibration cycle was cancelled." 
           --#ARGUMENTS {1}
           --#SEVERITY INFORMATIONAL
           --#TIMEINDEX 2
           --#STATE OPERATIONAL
           ::= 409

ctldevBbuNoBattery    TRAP-TYPE
    ENTERPRISE  eMylexRaidEventInformation
    VARIABLES   {
	a9EventCode,
	a9ControllerNumber,
	a9EventTimeStamp
    }
          DESCRIPTION
           "Battery is not present."
           --#SUMMARY  "[ctl: %d :] Battery is not present." 
           --#ARGUMENTS {1}
           --#SEVERITY MAJOR
           --#TIMEINDEX 2
           --#STATE DEGRADED
           ::= 410

ctldevConservCacheMode    TRAP-TYPE
    ENTERPRISE  eMylexRaidEventInformation
    VARIABLES   {
	a9EventCode,
	a9ControllerNumber,
	a9EventTimeStamp
    }
          DESCRIPTION
           "Controller entered conservative cache mode."
           --#SUMMARY  "[ctl: %d :] Controller entered conservative cache mode." 
           --#ARGUMENTS {1}
           --#SEVERITY INFORMATIONAL
           --#TIMEINDEX 2
           --#STATE OPERATIONAL
           ::= 411

ctldevNormalCacheMode    TRAP-TYPE
    ENTERPRISE  eMylexRaidEventInformation
    VARIABLES   {
	a9EventCode,
	a9ControllerNumber,
	a9EventTimeStamp
    }
          DESCRIPTION
           "Controller entered normal cache mode."
           --#SUMMARY  "[ctl: %d :] Controller entered normal cache mode." 
           --#ARGUMENTS {1}
           --#SEVERITY INFORMATIONAL
           --#TIMEINDEX 2
           --#STATE OPERATIONAL
           ::= 412

ctldevDevStartCmplt    TRAP-TYPE
    ENTERPRISE  eMylexRaidEventInformation
    VARIABLES   {
	a9EventCode,
	a9ControllerNumber,
	a9EventTimeStamp
    }
          DESCRIPTION
           "Controller device start complete."
           --#SUMMARY  "[ctl: %d :] Controller device start complete." 
           --#ARGUMENTS {1}
           --#SEVERITY INFORMATIONAL
           --#TIMEINDEX 2
           --#STATE OPERATIONAL
           ::= 413

ctldevSoftEccCorrected    TRAP-TYPE
    ENTERPRISE  eMylexRaidEventInformation
    VARIABLES   {
	a9EventCode,
	a9ControllerNumber,
	a9EventTimeStamp
    }
          DESCRIPTION
           "Soft ECC error corrected."
           --#SUMMARY  "[ctl: %d :] Soft ECC error corrected." 
           --#ARGUMENTS {1}
           --#SEVERITY MAJOR
           --#TIMEINDEX 2
           --#STATE DEGRADED
           ::= 414

ctldevHardEccCorrected    TRAP-TYPE
    ENTERPRISE  eMylexRaidEventInformation
    VARIABLES   {
	a9EventCode,
	a9ControllerNumber,
	a9ChannelNumber,
	a9TargetNumber,
	a9EventTimeStamp
    }
          DESCRIPTION
           "Hard ECC error corrected."
           --#SUMMARY  "[ctl: %d chn: %d tgt: %d :] Hard ECC error corrected." 
           --#ARGUMENTS {1,2,3}
           --#SEVERITY MAJOR
           --#TIMEINDEX 4
           --#STATE DEGRADED
           ::= 415

ctldevBbuRecondNeeded    TRAP-TYPE
    ENTERPRISE  eMylexRaidEventInformation
    VARIABLES   {
	a9EventCode,
	a9ControllerNumber,
	a9EventTimeStamp
    }
          DESCRIPTION
           "Battery recondition suggested."
           --#SUMMARY  "[ctl: %d :] Battery recondition suggested." 
           --#ARGUMENTS {1}
           --#SEVERITY INFORMATIONAL
           --#TIMEINDEX 2
           --#STATE OPERATIONAL
           ::= 416

ctldevRemovedPtnr    TRAP-TYPE
    ENTERPRISE  eMylexRaidEventInformation
    VARIABLES   {
	a9EventCode,
	a9ControllerNumber,
	a9EventTimeStamp
    }
          DESCRIPTION
           "Controller's partner has been removed."
           --#SUMMARY  "[ctl: %d :] Controller's partner has been removed." 
           --#ARGUMENTS {1}
           --#SEVERITY MINOR
           --#TIMEINDEX 2
           --#STATE OPERATIONAL
           ::= 417

ctldevBbuOutOfService    TRAP-TYPE
    ENTERPRISE  eMylexRaidEventInformation
    VARIABLES   {
	a9EventCode,
	a9ControllerNumber,
	a9EventTimeStamp
    }
          DESCRIPTION
           "BBU out of service."
           --#SUMMARY  "[ctl: %d :] BBU out of service." 
           --#ARGUMENTS {1}
           --#SEVERITY MAJOR
           --#TIMEINDEX 2
           --#STATE DEGRADED
           ::= 418

ctldevUpdatePtnrStatus    TRAP-TYPE
    ENTERPRISE  eMylexRaidEventInformation
    VARIABLES   {
	a9EventCode,
	a9ControllerNumber,
	a9EventTimeStamp
    }
          DESCRIPTION
           "Updated partner's status."
           --#SUMMARY  "[ctl: %d :] Updated partner's status." 
           --#ARGUMENTS {1}
           --#SEVERITY INFORMATIONAL
           --#TIMEINDEX 2
           --#STATE OPERATIONAL
           ::= 419

ctldevRelinquishPtnr    TRAP-TYPE
    ENTERPRISE  eMylexRaidEventInformation
    VARIABLES   {
	a9EventCode,
	a9ControllerNumber,
	a9EventTimeStamp
    }
          DESCRIPTION
           "Relinquished partner."
           --#SUMMARY  "[ctl: %d :] Relinquished partner." 
           --#ARGUMENTS {1}
           --#SEVERITY INFORMATIONAL
           --#TIMEINDEX 2
           --#STATE OPERATIONAL
           ::= 420

ctldevInsertedPtnr    TRAP-TYPE
    ENTERPRISE  eMylexRaidEventInformation
    VARIABLES   {
	a9EventCode,
	a9ControllerNumber,
	a9EventTimeStamp
    }
          DESCRIPTION
           "Inserted partner."
           --#SUMMARY  "[ctl: %d :] Inserted partner." 
           --#ARGUMENTS {1}
           --#SEVERITY MINOR
           --#TIMEINDEX 2
           --#STATE OPERATIONAL
           ::= 421

ctldevDualEnabled    TRAP-TYPE
    ENTERPRISE  eMylexRaidEventInformation
    VARIABLES   {
	a9EventCode,
	a9ControllerNumber,
	a9EventTimeStamp
    }
          DESCRIPTION
           "Dual controllers enabled."
           --#SUMMARY  "[ctl: %d :] Dual controllers enabled." 
           --#ARGUMENTS {1}
           --#SEVERITY INFORMATIONAL
           --#TIMEINDEX 2
           --#STATE OPERATIONAL
           ::= 422

ctldevKillPtnr    TRAP-TYPE
    ENTERPRISE  eMylexRaidEventInformation
    VARIABLES   {
	a9EventCode,
	a9ControllerNumber,
	a9EventTimeStamp
    }
          DESCRIPTION
           "Disabled partner."
           --#SUMMARY  "[ctl: %d :] Disabled partner." 
           --#ARGUMENTS {1}
           --#SEVERITY MAJOR
           --#TIMEINDEX 2
           --#STATE DEGRADED
           ::= 423

ctldevNexus    TRAP-TYPE
    ENTERPRISE  eMylexRaidEventInformation
    VARIABLES   {
	a9EventCode,
	a9ControllerNumber,
	a9EventTimeStamp
    }
          DESCRIPTION
           "Dual controllers entered nexus."
           --#SUMMARY  "[ctl: %d :] Dual controllers entered nexus." 
           --#ARGUMENTS {1}
           --#SEVERITY INFORMATIONAL
           --#TIMEINDEX 2
           --#STATE OPERATIONAL
           ::= 424

ctldevBadBootromImage    TRAP-TYPE
    ENTERPRISE  eMylexRaidEventInformation
    VARIABLES   {
	a9EventCode,
	a9ControllerNumber,
	a9EventTimeStamp
    }
          DESCRIPTION
           "Controller boot ROM image needs to be reloaded."
           --#SUMMARY  "[ctl: %d :] Controller boot ROM image needs to be reloaded." 
           --#ARGUMENTS {1}
           --#SEVERITY MAJOR
           --#TIMEINDEX 2
           --#STATE DEGRADED
           ::= 425

ctldevBadMacAddress    TRAP-TYPE
    ENTERPRISE  eMylexRaidEventInformation
    VARIABLES   {
	a9EventCode,
	a9ControllerNumber,
	a9EventTimeStamp
    }
          DESCRIPTION
           "Controller is using default non-unique world-wide name."
           --#SUMMARY  "[ctl: %d :] Controller is using default non-unique world-wide name." 
           --#ARGUMENTS {1}
           --#SEVERITY MAJOR
           --#TIMEINDEX 2
           --#STATE DEGRADED
           ::= 426

ctldevMirrorRaceRecoveryFailed    TRAP-TYPE
    ENTERPRISE  eMylexRaidEventInformation
    VARIABLES   {
	a9EventCode,
	a9ControllerNumber,
	a9EventTimeStamp
    }
          DESCRIPTION
           "Mirror Race recovery failed."
           --#SUMMARY  "[ctl: %d :] Mirror Race recovery failed." 
           --#ARGUMENTS {1}
           --#SEVERITY MAJOR
           --#TIMEINDEX 2
           --#STATE DEGRADED
           ::= 427

ctldevMirrorCriticalDrive    TRAP-TYPE
    ENTERPRISE  eMylexRaidEventInformation
    VARIABLES   {
	a9EventCode,
	a9ControllerNumber,
	a9EventTimeStamp
    }
          DESCRIPTION
           "Mirror Race on critical logical drive."
           --#SUMMARY  "[ctl: %d :] Mirror Race on critical logical drive." 
           --#ARGUMENTS {1}
           --#SEVERITY MAJOR
           --#TIMEINDEX 2
           --#STATE DEGRADED
           ::= 428

ctldevInCluster    TRAP-TYPE
    ENTERPRISE  eMylexRaidEventInformation
    VARIABLES   {
	a9EventCode,
	a9EventTimeStamp
    }
          DESCRIPTION
           "Controller connected to cluster."
           --#SUMMARY  "    Controller connected to cluster." 
           --#ARGUMENTS {}
           --#SEVERITY INFORMATIONAL
           --#TIMEINDEX 1
           --#STATE OPERATIONAL
           ::= 429

ctldevNotInCluster    TRAP-TYPE
    ENTERPRISE  eMylexRaidEventInformation
    VARIABLES   {
	a9EventCode,
	a9EventTimeStamp
    }
          DESCRIPTION
           "Controller disconnected from cluster."
           --#SUMMARY  "    Controller disconnected from cluster." 
           --#ARGUMENTS {}
           --#SEVERITY INFORMATIONAL
           --#TIMEINDEX 1
           --#STATE OPERATIONAL
           ::= 430

sysdevDataLossImproperShutdown    TRAP-TYPE
    ENTERPRISE  eMylexRaidEventInformation
    VARIABLES   {
	a9EventCode,
	a9ControllerNumber,
	a9LogicalDriveNumber,
	a9EventTimeStamp
    }
          DESCRIPTION
           "Controller improperly shutdown! Data may have been lost."
           --#SUMMARY  "[ctl: %d logdrv: %d :] Controller improperly shutdown! Data may have been lost." 
           --#ARGUMENTS {1,2}
           --#SEVERITY MAJOR
           --#TIMEINDEX 3
           --#STATE DEGRADED
           ::= 431

ctldevAutomaticFlashStarted    TRAP-TYPE
    ENTERPRISE  eMylexRaidEventInformation
    VARIABLES   {
	a9EventCode,
	a9ControllerNumber,
	a9EventTimeStamp
    }
          DESCRIPTION
           "Dual-active automatic flash of replacement controller."
           --#SUMMARY  "[ctl: %d :] Dual-active automatic flash of replacement controller." 
           --#ARGUMENTS {1}
           --#SEVERITY INFORMATIONAL
           --#TIMEINDEX 2
           --#STATE OPERATIONAL
           ::= 432

ctldevNegotiationFailedJumpers    TRAP-TYPE
    ENTERPRISE  eMylexRaidEventInformation
    VARIABLES   {
	a9EventCode,
	a9ControllerNumber,
	a9EventTimeStamp
    }
          DESCRIPTION
           "Dual-active negotiation failed jumpers."
           --#SUMMARY  "[ctl: %d :] Dual-active negotiation failed jumpers." 
           --#ARGUMENTS {1}
           --#SEVERITY MAJOR
           --#TIMEINDEX 2
           --#STATE DEGRADED
           ::= 433

ctldevNegotiationSameId    TRAP-TYPE
    ENTERPRISE  eMylexRaidEventInformation
    VARIABLES   {
	a9EventCode,
	a9ControllerNumber,
	a9EventTimeStamp
    }
          DESCRIPTION
           "Dual-active negotiation failed IDs."
           --#SUMMARY  "[ctl: %d :] Dual-active negotiation failed IDs." 
           --#ARGUMENTS {1}
           --#SEVERITY MAJOR
           --#TIMEINDEX 2
           --#STATE DEGRADED
           ::= 434

ctldevNegotiationBoardType    TRAP-TYPE
    ENTERPRISE  eMylexRaidEventInformation
    VARIABLES   {
	a9EventCode,
	a9ControllerNumber,
	a9EventTimeStamp
    }
          DESCRIPTION
           "Dual-active negotiation failed board types."
           --#SUMMARY  "[ctl: %d :] Dual-active negotiation failed board types." 
           --#ARGUMENTS {1}
           --#SEVERITY MAJOR
           --#TIMEINDEX 2
           --#STATE DEGRADED
           ::= 435

ctldevNegotiationDiskChannels    TRAP-TYPE
    ENTERPRISE  eMylexRaidEventInformation
    VARIABLES   {
	a9EventCode,
	a9ControllerNumber,
	a9EventTimeStamp
    }
          DESCRIPTION
           "Dual-active negotiation failed disk channels."
           --#SUMMARY  "[ctl: %d :] Dual-active negotiation failed disk channels." 
           --#ARGUMENTS {1}
           --#SEVERITY MAJOR
           --#TIMEINDEX 2
           --#STATE DEGRADED
           ::= 436

ctldevNegotiationHostChannels    TRAP-TYPE
    ENTERPRISE  eMylexRaidEventInformation
    VARIABLES   {
	a9EventCode,
	a9ControllerNumber,
	a9EventTimeStamp
    }
          DESCRIPTION
           "Dual-active negotiation failed host ports."
           --#SUMMARY  "[ctl: %d :] Dual-active negotiation failed host ports." 
           --#ARGUMENTS {1}
           --#SEVERITY MAJOR
           --#TIMEINDEX 2
           --#STATE DEGRADED
           ::= 437

ctldevNegotiationMemorySize    TRAP-TYPE
    ENTERPRISE  eMylexRaidEventInformation
    VARIABLES   {
	a9EventCode,
	a9ControllerNumber,
	a9EventTimeStamp
    }
          DESCRIPTION
           "Dual-active negotiation failed memory size."
           --#SUMMARY  "[ctl: %d :] Dual-active negotiation failed memory size." 
           --#ARGUMENTS {1}
           --#SEVERITY MAJOR
           --#TIMEINDEX 2
           --#STATE DEGRADED
           ::= 438

ctldevNegotiationCacheSize    TRAP-TYPE
    ENTERPRISE  eMylexRaidEventInformation
    VARIABLES   {
	a9EventCode,
	a9ControllerNumber,
	a9EventTimeStamp
    }
          DESCRIPTION
           "Dual-active negotiation failed cache memory size."
           --#SUMMARY  "[ctl: %d :] Dual-active negotiation failed cache memory size." 
           --#ARGUMENTS {1}
           --#SEVERITY MAJOR
           --#TIMEINDEX 2
           --#STATE DEGRADED
           ::= 439

ctldevMirrorRaceTableError    TRAP-TYPE
    ENTERPRISE  eMylexRaidEventInformation
    VARIABLES   {
	a9EventCode,
	a9ControllerNumber,
	a9LogicalDriveNumber,
	a9EventTimeStamp
    }
          DESCRIPTION
           "Error in Mirror Race Table."
           --#SUMMARY  "[ctl: %d logdrv: %d :] Error in Mirror Race Table." 
           --#ARGUMENTS {1,2}
           --#SEVERITY MAJOR
           --#TIMEINDEX 3
           --#STATE DEGRADED
           ::= 440

ctldevStopRejected    TRAP-TYPE
    ENTERPRISE  eMylexRaidEventInformation
    VARIABLES   {
	a9EventCode,
	a9ControllerNumber,
	a9EventTimeStamp
    }
          DESCRIPTION
           "A replacement controller attempted to stop the surviving controller."
           --#SUMMARY  "[ctl: %d :] A replacement controller attempted to stop the surviving controller." 
           --#ARGUMENTS {1}
           --#SEVERITY MAJOR
           --#TIMEINDEX 2
           --#STATE DEGRADED
           ::= 441

ctldevPatrolreadIterationDone    TRAP-TYPE
    ENTERPRISE  eMylexRaidEventInformation
    VARIABLES   {
	a9EventCode,
	a9ControllerNumber,
	a9EventTimeStamp
    }
          DESCRIPTION
           "Patrol Read iteration completed."
           --#SUMMARY  "[ctl: %d :] Patrol Read iteration completed." 
           --#ARGUMENTS {1}
           --#SEVERITY INFORMATIONAL
           --#TIMEINDEX 2
           --#STATE OPERATIONAL
           ::= 442

ctldevWritebackToWritethru    TRAP-TYPE
    ENTERPRISE  eMylexRaidEventInformation
    VARIABLES   {
	a9EventCode,
	a9ControllerNumber,
	a9EventTimeStamp
    }
          DESCRIPTION
           "Controller entered 'Write Through' cache mode."
           --#SUMMARY  "[ctl: %d :] Controller entered 'Write Through' cache mode." 
           --#ARGUMENTS {1}
           --#SEVERITY INFORMATIONAL
           --#TIMEINDEX 2
           --#STATE OPERATIONAL
           ::= 443

ctldevWritethruToWriteback    TRAP-TYPE
    ENTERPRISE  eMylexRaidEventInformation
    VARIABLES   {
	a9EventCode,
	a9ControllerNumber,
	a9EventTimeStamp
    }
          DESCRIPTION
           "Controller entered 'Write Back' cache mode."
           --#SUMMARY  "[ctl: %d :] Controller entered 'Write Back' cache mode." 
           --#ARGUMENTS {1}
           --#SEVERITY INFORMATIONAL
           --#TIMEINDEX 2
           --#STATE OPERATIONAL
           ::= 444

ctldevUpdateFromPeer    TRAP-TYPE
    ENTERPRISE  eMylexRaidEventInformation
    VARIABLES   {
	a9EventCode,
	a9ControllerNumber,
	a9EventTimeStamp
    }
          DESCRIPTION
           "Update device state request sent from the peer controller."
           --#SUMMARY  "[ctl: %d :] Update device state request sent from the peer controller." 
           --#ARGUMENTS {1}
           --#SEVERITY INFORMATIONAL
           --#TIMEINDEX 2
           --#STATE OPERATIONAL
           ::= 445

ctldevCacheFlushed    TRAP-TYPE
    ENTERPRISE  eMylexRaidEventInformation
    VARIABLES   {
	a9EventCode,
	a9ControllerNumber,
	a9EventTimeStamp
    }
          DESCRIPTION
           "Data in Cache flushed during power up."
           --#SUMMARY  "[ctl: %d :] Data in Cache flushed during power up." 
           --#ARGUMENTS {1}
           --#SEVERITY INFORMATIONAL
           --#TIMEINDEX 2
           --#STATE OPERATIONAL
           ::= 446

ctldevCacheNotFlushed    TRAP-TYPE
    ENTERPRISE  eMylexRaidEventInformation
    VARIABLES   {
	a9EventCode,
	a9ControllerNumber,
	a9EventTimeStamp
    }
          DESCRIPTION
           "Data in Cache not flushed during power up."
           --#SUMMARY  "[ctl: %d :] Data in Cache not flushed during power up." 
           --#ARGUMENTS {1}
           --#SEVERITY MAJOR
           --#TIMEINDEX 2
           --#STATE DEGRADED
           ::= 447          
           
ctldevCcRateChanged    TRAP-TYPE
    ENTERPRISE  eMylexRaidEventInformation
    VARIABLES   {
	a9EventCode,
	a9ControllerNumber,
	a9EventTimeStamp
    }
          DESCRIPTION
           "Consistency Check rate changed."
           --#SUMMARY  "[ctl: %d :] Consistency Check rate changed." 
           --#ARGUMENTS {1}
           --#SEVERITY INFORMATIONAL
           --#TIMEINDEX 2
           --#STATE OPERATIONAL
           ::= 448          

ctldevBgiRateChanged    TRAP-TYPE
    ENTERPRISE  eMylexRaidEventInformation
    VARIABLES   {
	a9EventCode,
	a9ControllerNumber,
	a9EventTimeStamp
    }
          DESCRIPTION
           "Background initialization rate changed."
           --#SUMMARY  "[ctl: %d :] Background initialization rate changed." 
           --#ARGUMENTS {1}
           --#SEVERITY INFORMATIONAL
           --#TIMEINDEX 2
           --#STATE OPERATIONAL
           ::= 449          

ctldevFlushRateChanged    TRAP-TYPE
    ENTERPRISE  eMylexRaidEventInformation
    VARIABLES   {
	a9EventCode,
	a9ControllerNumber,
	a9EventTimeStamp
    }
          DESCRIPTION
           "Flush rate changed."
           --#SUMMARY  "[ctl: %d :] Flush rate changed." 
           --#ARGUMENTS {1}
           --#SEVERITY INFORMATIONAL
           --#TIMEINDEX 2
           --#STATE OPERATIONAL
           ::= 450         

ctldevPrRateChanged    TRAP-TYPE
    ENTERPRISE  eMylexRaidEventInformation
    VARIABLES   {
	a9EventCode,
	a9ControllerNumber,
	a9EventTimeStamp
    }
          DESCRIPTION
           "Patrol Read Rate changed."
           --#SUMMARY  "[ctl: %d :] Patrol Read Rate changed." 
           --#ARGUMENTS {1}
           --#SEVERITY INFORMATIONAL
           --#TIMEINDEX 2
           --#STATE OPERATIONAL
           ::= 451          

ctldevRbldRateChanged    TRAP-TYPE
    ENTERPRISE  eMylexRaidEventInformation
    VARIABLES   {
	a9EventCode,
	a9ControllerNumber,
	a9EventTimeStamp
    }
          DESCRIPTION
           "Rebuild rate changed."
           --#SUMMARY  "[ctl: %d :] Rebuild rate changed." 
           --#ARGUMENTS {1}
           --#SEVERITY INFORMATIONAL
           --#TIMEINDEX 2
           --#STATE OPERATIONAL
           ::= 452          

ctldevReconRateChanged    TRAP-TYPE
    ENTERPRISE  eMylexRaidEventInformation
    VARIABLES   {
	a9EventCode,
	a9ControllerNumber,
	a9EventTimeStamp
    }
          DESCRIPTION
           "Reconstruction rate changed."
           --#SUMMARY  "[ctl: %d :] Reconstruction rate changed." 
           --#ARGUMENTS {1}
           --#SEVERITY INFORMATIONAL
           --#TIMEINDEX 2
           --#STATE OPERATIONAL
           ::= 453          

ctldevClusterDown    TRAP-TYPE
    ENTERPRISE  eMylexRaidEventInformation
    VARIABLES   {
	a9EventCode,
	a9ControllerNumber,
	a9EventTimeStamp
    }
          DESCRIPTION
           "Cluster down; communication with peer lost."
           --#SUMMARY  "[ctl: %d :] Cluster down; communication with peer lost." 
           --#ARGUMENTS {1}
           --#SEVERITY MAJOR
           --#TIMEINDEX 2
           --#STATE OPERATIONAL
           ::= 454          

ctldevAlarmDisabled    TRAP-TYPE
    ENTERPRISE  eMylexRaidEventInformation
    VARIABLES   {
	a9EventCode,
	a9ControllerNumber,
	a9EventTimeStamp
    }
          DESCRIPTION
           "Alarm disabled by user."
           --#SUMMARY  "[ctl: %d :] Alarm disabled by user." 
           --#ARGUMENTS {1}
           --#SEVERITY INFORMATIONAL
           --#TIMEINDEX 2
           --#STATE OPERATIONAL
           ::= 455          

ctldevAlarmEnabled    TRAP-TYPE
    ENTERPRISE  eMylexRaidEventInformation
    VARIABLES   {
	a9EventCode,
	a9ControllerNumber,
	a9EventTimeStamp
    }
          DESCRIPTION
           "Alarm enabled by user."
           --#SUMMARY  "[ctl: %d :] Alarm enabled by user." 
           --#ARGUMENTS {1}
           --#SEVERITY INFORMATIONAL
           --#TIMEINDEX 2
           --#STATE OPERATIONAL
           ::= 456          

ctldevCacheRebootCantRecover    TRAP-TYPE
    ENTERPRISE  eMylexRaidEventInformation
    VARIABLES   {
	a9EventCode,
	a9ControllerNumber,
	a9EventTimeStamp
    }
          DESCRIPTION
           "Unable to recover cache data due to configuration mismatch."
           --#SUMMARY  "[ctl: %d :] Unable to recover cache data due to configuration mismatch." 
           --#ARGUMENTS {1}
           --#SEVERITY MAJOR
           --#TIMEINDEX 2
           --#STATE OPERATIONAL
           ::= 457          

ctldevCacheRebootRecover    TRAP-TYPE
    ENTERPRISE  eMylexRaidEventInformation
    VARIABLES   {
	a9EventCode,
	a9ControllerNumber,
	a9EventTimeStamp
    }
          DESCRIPTION
           "Cache data recovered successfully."
           --#SUMMARY  "[ctl: %d :] Cache data recovered successfully." 
           --#ARGUMENTS {1}
           --#SEVERITY MAJOR
           --#TIMEINDEX 2
           --#STATE OPERATIONAL
           ::= 458          

ctldevCacheVersionMismatch    TRAP-TYPE
    ENTERPRISE  eMylexRaidEventInformation
    VARIABLES   {
	a9EventCode,
	a9ControllerNumber,
	a9EventTimeStamp
    }
          DESCRIPTION
           "Controller cache discarded due to firmware version incompatibility."
           --#SUMMARY  "[ctl: %d :] Controller cache discarded due to firmware version incompatibility." 
           --#ARGUMENTS {1}
           --#SEVERITY INFORMATIONAL
           --#TIMEINDEX 2
           --#STATE OPERATIONAL
           ::= 459          

ctldevFactoryDefaults    TRAP-TYPE
    ENTERPRISE  eMylexRaidEventInformation
    VARIABLES   {
	a9EventCode,
	a9ControllerNumber,
	a9EventTimeStamp
    }
          DESCRIPTION
           "Factory defaults restored."
           --#SUMMARY  "[ctl: %d :] Factory defaults restored." 
           --#ARGUMENTS {1}
           --#SEVERITY INFORMATIONAL
           --#TIMEINDEX 2
           --#STATE OPERATIONAL
           ::= 460          

ctldevHibernate    TRAP-TYPE
    ENTERPRISE  eMylexRaidEventInformation
    VARIABLES   {
	a9EventCode,
	a9ControllerNumber,
	a9EventTimeStamp
    }
          DESCRIPTION
           "Hibernate command received from host."
           --#SUMMARY  "[ctl: %d :] Hibernate command received from host." 
           --#ARGUMENTS {1}
           --#SEVERITY INFORMATIONAL
           --#TIMEINDEX 2
           --#STATE OPERATIONAL
           ::= 461          

ctldevLogCleared    TRAP-TYPE
    ENTERPRISE  eMylexRaidEventInformation
    VARIABLES   {
	a9EventCode,
	a9ControllerNumber,
	a9EventTimeStamp
    }
          DESCRIPTION
           "Event log cleared."
           --#SUMMARY  "[ctl: %d :] Event log cleared." 
           --#ARGUMENTS {1}
           --#SEVERITY INFORMATIONAL
           --#TIMEINDEX 2
           --#STATE OPERATIONAL
           ::= 462          

ctldevLogWrapped    TRAP-TYPE
    ENTERPRISE  eMylexRaidEventInformation
    VARIABLES   {
	a9EventCode,
	a9ControllerNumber,
	a9EventTimeStamp
    }
          DESCRIPTION
           "Event log wrapped."
           --#SUMMARY  "[ctl: %d :] Event log wrapped." 
           --#ARGUMENTS {1}
           --#SEVERITY INFORMATIONAL
           --#TIMEINDEX 2
           --#STATE OPERATIONAL
           ::= 463          

ctldevNotEnoughMemory    TRAP-TYPE
    ENTERPRISE  eMylexRaidEventInformation
    VARIABLES   {
	a9EventCode,
	a9ControllerNumber,
	a9EventTimeStamp
    }
          DESCRIPTION
           "Not enough controller memory."
           --#SUMMARY  "[ctl: %d :] Not enough controller memory." 
           --#ARGUMENTS {1}
           --#SEVERITY MAJOR
           --#TIMEINDEX 2
           --#STATE OPERATIONAL
           ::= 464          

ctldevPrPause    TRAP-TYPE
    ENTERPRISE  eMylexRaidEventInformation
    VARIABLES   {
	a9EventCode,
	a9ControllerNumber,
	a9EventTimeStamp
    }
          DESCRIPTION
           "Patrol Read paused."
           --#SUMMARY  "[ctl: %d :] Patrol Read paused." 
           --#ARGUMENTS {1}
           --#SEVERITY INFORMATIONAL
           --#TIMEINDEX 2
           --#STATE OPERATIONAL
           ::= 465          

ctldevPrResume    TRAP-TYPE
    ENTERPRISE  eMylexRaidEventInformation
    VARIABLES   {
	a9EventCode,
	a9ControllerNumber,
	a9EventTimeStamp
    }
          DESCRIPTION
           "Patrol Read resumed."
           --#SUMMARY  "[ctl: %d :] Patrol Read resumed." 
           --#ARGUMENTS {1}
           --#SEVERITY INFORMATIONAL
           --#TIMEINDEX 2
           --#STATE OPERATIONAL
           ::= 466          

ctldevPrStart    TRAP-TYPE
    ENTERPRISE  eMylexRaidEventInformation
    VARIABLES   {
	a9EventCode,
	a9ControllerNumber,
	a9EventTimeStamp
    }
          DESCRIPTION
           "Patrol Read started."
           --#SUMMARY  "[ctl: %d :] Patrol Read started." 
           --#ARGUMENTS {1}
           --#SEVERITY INFORMATIONAL
           --#TIMEINDEX 2
           --#STATE OPERATIONAL
           ::= 467          

ctldevShutdown    TRAP-TYPE
    ENTERPRISE  eMylexRaidEventInformation
    VARIABLES   {
	a9EventCode,
	a9ControllerNumber,
	a9EventTimeStamp
    }
          DESCRIPTION
           "Shutdown command received from host."
           --#SUMMARY  "[ctl: %d :] Shutdown command received from host." 
           --#ARGUMENTS {1}
           --#SEVERITY INFORMATIONAL
           --#TIMEINDEX 2
           --#STATE OPERATIONAL
           ::= 468          

ctldevUserEnteredDebugger    TRAP-TYPE
    ENTERPRISE  eMylexRaidEventInformation
    VARIABLES   {
	a9EventCode,
	a9ControllerNumber,
	a9EventTimeStamp
    }
          DESCRIPTION
           "User entered firmware debugger."
           --#SUMMARY  "[ctl: %d :] User entered firmware debugger." 
           --#ARGUMENTS {1}
           --#SEVERITY INFORMATIONAL
           --#TIMEINDEX 2
           --#STATE OPERATIONAL
           ::= 469          

ctldevBbuTempHigh    TRAP-TYPE
    ENTERPRISE  eMylexRaidEventInformation
    VARIABLES   {
	a9EventCode,
	a9ControllerNumber,
	a9EventTimeStamp
    }
          DESCRIPTION
           "Battery temperature is high."
           --#SUMMARY  "[ctl: %d :] Battery temperature is high." 
           --#ARGUMENTS {1}
           --#SEVERITY MAJOR
           --#TIMEINDEX 2
           --#STATE OPERATIONAL
           ::= 470          

ctldevBbuCharging    TRAP-TYPE
    ENTERPRISE  eMylexRaidEventInformation
    VARIABLES   {
	a9EventCode,
	a9ControllerNumber,
	a9EventTimeStamp
    }
          DESCRIPTION
           "Battery is charging."
           --#SUMMARY  "[ctl: %d :] Battery is charging." 
           --#ARGUMENTS {1}
           --#SEVERITY INFORMATIONAL
           --#TIMEINDEX 2
           --#STATE OPERATIONAL
           ::= 471          

ctldevBbuDischarging    TRAP-TYPE
    ENTERPRISE  eMylexRaidEventInformation
    VARIABLES   {
	a9EventCode,
	a9ControllerNumber,
	a9EventTimeStamp
    }
          DESCRIPTION
           "Battery is discharging."
           --#SUMMARY  "[ctl: %d :] Battery is discharging." 
           --#ARGUMENTS {1}
           --#SEVERITY MAJOR
           --#TIMEINDEX 2
           --#STATE OPERATIONAL
           ::= 472          

ctldevBbuReplacementNeeded    TRAP-TYPE
    ENTERPRISE  eMylexRaidEventInformation
    VARIABLES   {
	a9EventCode,
	a9ControllerNumber,
	a9EventTimeStamp
    }
          DESCRIPTION
           "Battery needs to be replaced."
           --#SUMMARY  "[ctl: %d :] Battery needs to be replaced." 
           --#ARGUMENTS {1}
           --#SEVERITY MAJOR
           --#TIMEINDEX 2
           --#STATE OPERATIONAL
           ::= 473          

ctldevBbuRelearnTimeout    TRAP-TYPE
    ENTERPRISE  eMylexRaidEventInformation
    VARIABLES   {
	a9EventCode,
	a9ControllerNumber,
	a9EventTimeStamp
    }
          DESCRIPTION
           "Battery relearn timed out."
           --#SUMMARY  "[ctl: %d :] Battery relearn timed out." 
           --#ARGUMENTS {1}
           --#SEVERITY MAJOR
           --#TIMEINDEX 2
           --#STATE OPERATIONAL
           ::= 474      
		   
ctldevBbuRelearnPending    TRAP-TYPE
    ENTERPRISE  eMylexRaidEventInformation
    VARIABLES   {
	a9EventCode,
	a9ControllerNumber,
	a9EventTimeStamp
    }
          DESCRIPTION
           "Battery relearn pending: Battery is under charge."
           --#SUMMARY  "[ctl: %d :] Battery relearn pending: Battery is under charge." 
           --#ARGUMENTS {1}
           --#SEVERITY INFORMATIONAL
           --#TIMEINDEX 2
           --#STATE OPERATIONAL
           ::= 475          

ctldevBbuBatteryCapBelowSohThres    TRAP-TYPE
    ENTERPRISE  eMylexRaidEventInformation
    VARIABLES   {
	a9EventCode,
	a9ControllerNumber,
	a9EventTimeStamp
    }
          DESCRIPTION
           "Current capacity of the battery is below SOH/3."
           --#SUMMARY  "[ctl: %d :] Current capacity of the battery is below SOH/3." 
           --#ARGUMENTS {1}
           --#SEVERITY INFORMATIONAL
           --#TIMEINDEX 2
           --#STATE OPERATIONAL
           ::= 476          

ctldevBbuBatteryCapAboveSohThres    TRAP-TYPE
    ENTERPRISE  eMylexRaidEventInformation
    VARIABLES   {
	a9EventCode,
	a9ControllerNumber,
	a9EventTimeStamp
    }
          DESCRIPTION
           "Current capacity of the battery is greater than SOH/3."
           --#SUMMARY  "[ctl: %d :] Current capacity of the battery is greater than SOH/3." 
           --#ARGUMENTS {1}
           --#SEVERITY INFORMATIONAL
           --#TIMEINDEX 2
           --#STATE OPERATIONAL
           ::= 477          

ctldevBbuGood    TRAP-TYPE
    ENTERPRISE  eMylexRaidEventInformation
    VARIABLES   {
	a9EventCode,
	a9ControllerNumber,
	a9EventTimeStamp
    }
          DESCRIPTION
           "BBU enabled; changing WT logical drives to WB."
           --#SUMMARY  "[ctl: %d :] BBU enabled; changing WT logical drives to WB." 
           --#ARGUMENTS {1}
           --#SEVERITY INFORMATIONAL
           --#TIMEINDEX 2
           --#STATE OPERATIONAL
           ::= 478          
            
ctldevBbuBad    TRAP-TYPE
    ENTERPRISE  eMylexRaidEventInformation
    VARIABLES   {
	a9EventCode,
	a9ControllerNumber,
	a9EventTimeStamp
    }
          DESCRIPTION
           "BBU disabled; changing WB logical drives to WT."
           --#SUMMARY  "[ctl: %d :] BBU disabled; changing WB logical drives to WT." 
           --#ARGUMENTS {1}
           --#SEVERITY MINOR
           --#TIMEINDEX 2
           --#STATE OPERATIONAL
           ::= 479    
		         
ctldevBbuRecondRequested    TRAP-TYPE
    ENTERPRISE  eMylexRaidEventInformation
    VARIABLES   {
	a9EventCode,
	a9ControllerNumber,
	a9EventTimeStamp
    }
          DESCRIPTION
           "Battery Relearn request received."
           --#SUMMARY  "[ctl: %d :] Battery Relearn request received." 
           --#ARGUMENTS {1}
           --#SEVERITY INFORMATIONAL
           --#TIMEINDEX 2
           --#STATE OPERATIONAL
           ::= 481          

ctldevCacheDiscardByUser    TRAP-TYPE
    ENTERPRISE  eMylexRaidEventInformation
    VARIABLES   {
	a9EventCode,
	a9ControllerNumber,
	a9EventTimeStamp
    }
          DESCRIPTION
           "Controller Cache discarded by user."
           --#SUMMARY  "[ctl: %d :] Controller Cache discarded by user." 
           --#ARGUMENTS {1}
           --#SEVERITY INFORMATIONAL
           --#TIMEINDEX 2
           --#STATE OPERATIONAL
           ::= 482          

ctldevBootConfigMissing    TRAP-TYPE
    ENTERPRISE  eMylexRaidEventInformation
    VARIABLES   {
	a9EventCode,
	a9ControllerNumber,
	a9EventTimeStamp
    }
          DESCRIPTION
           "Previous configuration is completely missing at boot."
           --#SUMMARY  "[ctl: %d :] Previous configuration is completely missing at boot." 
           --#ARGUMENTS {1}
           --#SEVERITY INFORMATIONAL
           --#TIMEINDEX 2
           --#STATE OPERATIONAL
           ::= 483          

systemStartedNew    TRAP-TYPE
    ENTERPRISE  eMylexRaidEventInformation
    VARIABLES   {
	a9EventCode,
	a9EventTimeStamp
    }
          DESCRIPTION
           "System started."
           --#SUMMARY  "    System started." 
           --#ARGUMENTS {}
           --#SEVERITY INFORMATIONAL
           --#TIMEINDEX 1
           --#STATE OPERATIONAL
           ::= 512

systemSizeTableFull    TRAP-TYPE
    ENTERPRISE  eMylexRaidEventInformation
    VARIABLES   {
	a9EventCode,
	a9EventTimeStamp
    }
          DESCRIPTION
           "Size table full."
           --#SUMMARY  "    Size table full." 
           --#ARGUMENTS {}
           --#SEVERITY INFORMATIONAL
           --#TIMEINDEX 1
           --#STATE OPERATIONAL
           ::= 513

systemUserLoggedIn    TRAP-TYPE
    ENTERPRISE  eMylexRaidEventInformation
    VARIABLES   {
	a9EventCode,
	a9EventTimeStamp
    }
          DESCRIPTION
           "User logged in."
           --#SUMMARY  "    User logged in." 
           --#ARGUMENTS {}
           --#SEVERITY INFORMATIONAL
           --#TIMEINDEX 1
           --#STATE OPERATIONAL
           ::= 514

systemUserLoggedOut    TRAP-TYPE
    ENTERPRISE  eMylexRaidEventInformation
    VARIABLES   {
	a9EventCode,
	a9EventTimeStamp
    }
          DESCRIPTION
           "User logged out."
           --#SUMMARY  "    User logged out." 
           --#ARGUMENTS {}
           --#SEVERITY INFORMATIONAL
           --#TIMEINDEX 1
           --#STATE OPERATIONAL
           ::= 515

systemAlive    TRAP-TYPE
    ENTERPRISE  eMylexRaidEventInformation
    VARIABLES   {
	a9EventCode,
	a9EventTimeStamp
    }
          DESCRIPTION
           "Server alive."
           --#SUMMARY  "    Server alive." 
           --#ARGUMENTS {}
           --#SEVERITY INFORMATIONAL
           --#TIMEINDEX 1
           --#STATE OPERATIONAL
           ::= 516

systemDead    TRAP-TYPE
    ENTERPRISE  eMylexRaidEventInformation
    VARIABLES   {
	a9EventCode,
	a9EventTimeStamp
    }
          DESCRIPTION
           "Lost connection to server, or server is down."
           --#SUMMARY  "    Lost connection to server, or server is down." 
           --#ARGUMENTS {}
           --#SEVERITY MAJOR
           --#TIMEINDEX 1
           --#STATE DEGRADED
           ::= 517

autobootChanged    TRAP-TYPE
    ENTERPRISE  eMylexRaidEventInformation
    VARIABLES   {
	a9EventCode,
	a9ControllerNumber,
	a9EventTimeStamp
    }
          DESCRIPTION
           "Automatic reboot count has changed."
           --#SUMMARY  "[ctl: %d :] Automatic reboot count has changed." 
           --#ARGUMENTS {1}
           --#SEVERITY INFORMATIONAL
           --#TIMEINDEX 2
           --#STATE OPERATIONAL
           ::= 518

ctldevBbuBattTestStart    TRAP-TYPE
    ENTERPRISE  eMylexRaidEventInformation
    VARIABLES   {
	a9EventCode,
	a9ControllerNumber,
	a9EventTimeStamp
    }
          DESCRIPTION
           "Battery test has started"
           --#SUMMARY  "[ctl: %d :] Battery test has started" 
           --#ARGUMENTS {1}
           --#SEVERITY INFORMATIONAL
           --#TIMEINDEX 2
           --#STATE OPERATIONAL
           ::= 519

ctldevBbuBattTestComplete    TRAP-TYPE
    ENTERPRISE  eMylexRaidEventInformation
    VARIABLES   {
	a9EventCode,
	a9ControllerNumber,
	a9EventTimeStamp
    }
          DESCRIPTION
           "Battery test complete"
           --#SUMMARY  "[ctl: %d :] Battery test complete" 
           --#ARGUMENTS {1}
           --#SEVERITY INFORMATIONAL
           --#TIMEINDEX 2
           --#STATE OPERATIONAL
           ::= 520

ctldevBbuBattTestCanceled    TRAP-TYPE
    ENTERPRISE  eMylexRaidEventInformation
    VARIABLES   {
	a9EventCode,
	a9ControllerNumber,
	a9EventTimeStamp
    }
          DESCRIPTION
           "Battery test canceled"
           --#SUMMARY  "[ctl: %d :] Battery test canceled" 
           --#ARGUMENTS {1}
           --#SEVERITY INFORMATIONAL
           --#TIMEINDEX 2
           --#STATE OPERATIONAL
           ::= 521

ctldevBbuBattTestFailed    TRAP-TYPE
    ENTERPRISE  eMylexRaidEventInformation
    VARIABLES   {
	a9EventCode,
	a9ControllerNumber,
	a9EventTimeStamp
    }
          DESCRIPTION
           "Battery test failed - battery bad"
           --#SUMMARY  "[ctl: %d :] Battery test failed - battery bad" 
           --#ARGUMENTS {1}
           --#SEVERITY MAJOR
           --#TIMEINDEX 2
           --#STATE DEGRADED
           ::= 522

channelFailed    TRAP-TYPE
    ENTERPRISE  eMylexRaidEventInformation
    VARIABLES   {
	a9EventCode,
	a9ControllerNumber,
	a9ChannelNumber,
	a9EventTimeStamp
    }
          DESCRIPTION
           "Channel Failed."
           --#SUMMARY  "[ctl: %d chn: %d :] Channel Failed." 
           --#ARGUMENTS {1,2}
           --#SEVERITY MINOR
           --#TIMEINDEX 3
           --#STATE OPERATIONAL
           ::= 640

channelOk    TRAP-TYPE
    ENTERPRISE  eMylexRaidEventInformation
    VARIABLES   {
	a9EventCode,
	a9ControllerNumber,
	a9ChannelNumber,
	a9EventTimeStamp
    }
          DESCRIPTION
           "Channel Online."
           --#SUMMARY  "[ctl: %d chn: %d :] Channel Online." 
           --#ARGUMENTS {1,2}
           --#SEVERITY MINOR
           --#TIMEINDEX 3
           --#STATE OPERATIONAL
           ::= 641

channelScsiBusDead    TRAP-TYPE
    ENTERPRISE  eMylexRaidEventInformation
    VARIABLES   {
	a9EventCode,
	a9ControllerNumber,
	a9ChannelNumber,
	a9EventTimeStamp
    }
          DESCRIPTION
           "Back end SCSI bus dead."
           --#SUMMARY  "[ctl: %d chn: %d :] Back end SCSI bus dead." 
           --#ARGUMENTS {1,2}
           --#SEVERITY MAJOR
           --#TIMEINDEX 3
           --#STATE DEGRADED
           ::= 642

channelScsiBusAlive    TRAP-TYPE
    ENTERPRISE  eMylexRaidEventInformation
    VARIABLES   {
	a9EventCode,
	a9ControllerNumber,
	a9ChannelNumber,
	a9EventTimeStamp
    }
          DESCRIPTION
           "Back end SCSI bus alive."
           --#SUMMARY  "[ctl: %d chn: %d :] Back end SCSI bus alive." 
           --#ARGUMENTS {1,2}
           --#SEVERITY INFORMATIONAL
           --#TIMEINDEX 3
           --#STATE OPERATIONAL
           ::= 643

channelFiberDead    TRAP-TYPE
    ENTERPRISE  eMylexRaidEventInformation
    VARIABLES   {
	a9EventCode,
	a9ControllerNumber,
	a9ChannelNumber,
	a9EventTimeStamp
    }
          DESCRIPTION
           "Back end fibre dead."
           --#SUMMARY  "[ctl: %d chn: %d :] Back end fibre dead." 
           --#ARGUMENTS {1,2}
           --#SEVERITY MAJOR
           --#TIMEINDEX 3
           --#STATE DEGRADED
           ::= 644

channelFiberAlive    TRAP-TYPE
    ENTERPRISE  eMylexRaidEventInformation
    VARIABLES   {
	a9EventCode,
	a9ControllerNumber,
	a9ChannelNumber,
	a9EventTimeStamp
    }
          DESCRIPTION
           "Back end fibre alive."
           --#SUMMARY  "[ctl: %d chn: %d :] Back end fibre alive." 
           --#ARGUMENTS {1,2}
           --#SEVERITY INFORMATIONAL
           --#TIMEINDEX 3
           --#STATE OPERATIONAL
           ::= 645

logEmpty    TRAP-TYPE
    ENTERPRISE  eMylexRaidEventInformation
    VARIABLES   {
	a9EventCode,
	a9ControllerNumber,
	a9EventTimeStamp
    }
          DESCRIPTION
           "Event log empty."
           --#SUMMARY  "[ctl: %d :] Event log empty." 
           --#ARGUMENTS {1}
           --#SEVERITY INFORMATIONAL
           --#TIMEINDEX 2
           --#STATE OPERATIONAL
           ::= 700

logOutSync    TRAP-TYPE
    ENTERPRISE  eMylexRaidEventInformation
    VARIABLES   {
	a9EventCode,
	a9ControllerNumber,
	a9EventTimeStamp
    }
          DESCRIPTION
           "Event log entries lost."
           --#SUMMARY  "[ctl: %d :] Event log entries lost." 
           --#ARGUMENTS {1}
           --#SEVERITY INFORMATIONAL
           --#TIMEINDEX 2
           --#STATE OPERATIONAL
           ::= 701

logRequestSense    TRAP-TYPE
    ENTERPRISE  eMylexRaidEventInformation
    VARIABLES   {
	a9EventCode,
	a9ControllerNumber,
	a9ChannelNumber,
	a9TargetNumber,
	a9EventTimeStamp
    }
          DESCRIPTION
           "Request Sense"
           --#SUMMARY  "[ctl: %d chn: %d tgt: %d :] Request Sense" 
           --#ARGUMENTS {1,2,3}
           --#SEVERITY INFORMATIONAL
           --#TIMEINDEX 4
           --#STATE OPERATIONAL
           ::= 702

logSetRtc    TRAP-TYPE
    ENTERPRISE  eMylexRaidEventInformation
    VARIABLES   {
	a9EventCode,
	a9ControllerNumber,
	a9ChannelNumber,
	a9EventTimeStamp
    }
          DESCRIPTION
           "Set real time clock."
           --#SUMMARY  "[ctl: %d chn: %d :] Set real time clock." 
           --#ARGUMENTS {1,2}
           --#SEVERITY INFORMATIONAL
           --#TIMEINDEX 3
           --#STATE OPERATIONAL
           ::= 703

cfgNew    TRAP-TYPE
    ENTERPRISE  eMylexRaidEventInformation
    VARIABLES   {
	a9EventCode,
	a9ControllerNumber,
	a9EventTimeStamp
    }
          DESCRIPTION
           "New configuration received."
           --#SUMMARY  "[ctl: %d :] New configuration received." 
           --#ARGUMENTS {1}
           --#SEVERITY INFORMATIONAL
           --#TIMEINDEX 2
           --#STATE OPERATIONAL
           ::= 800

cfgClear    TRAP-TYPE
    ENTERPRISE  eMylexRaidEventInformation
    VARIABLES   {
	a9EventCode,
	a9ControllerNumber,
	a9EventTimeStamp
    }
          DESCRIPTION
           "Configuration cleared."
           --#SUMMARY  "[ctl: %d :] Configuration cleared." 
           --#ARGUMENTS {1}
           --#SEVERITY INFORMATIONAL
           --#TIMEINDEX 2
           --#STATE OPERATIONAL
           ::= 801

cfgInvalid    TRAP-TYPE
    ENTERPRISE  eMylexRaidEventInformation
    VARIABLES   {
	a9EventCode,
	a9ControllerNumber,
	a9EventTimeStamp
    }
          DESCRIPTION
           "Configuration invalid."
           --#SUMMARY  "[ctl: %d :] Configuration invalid." 
           --#ARGUMENTS {1}
           --#SEVERITY MINOR
           --#TIMEINDEX 2
           --#STATE OPERATIONAL
           ::= 802

cfgCodAccessError    TRAP-TYPE
    ENTERPRISE  eMylexRaidEventInformation
    VARIABLES   {
	a9EventCode,
	a9ControllerNumber,
	a9EventTimeStamp
    }
          DESCRIPTION
           "Configuration on disk access error."
           --#SUMMARY  "[ctl: %d :] Configuration on disk access error." 
           --#ARGUMENTS {1}
           --#SEVERITY MINOR
           --#TIMEINDEX 2
           --#STATE OPERATIONAL
           ::= 803

cfgCodConverted    TRAP-TYPE
    ENTERPRISE  eMylexRaidEventInformation
    VARIABLES   {
	a9EventCode,
	a9ControllerNumber,
	a9EventTimeStamp
    }
          DESCRIPTION
           "Configuration on disk converted."
           --#SUMMARY  "[ctl: %d :] Configuration on disk converted." 
           --#ARGUMENTS {1}
           --#SEVERITY MINOR
           --#TIMEINDEX 2
           --#STATE OPERATIONAL
           ::= 804

cfgCodImportFailed    TRAP-TYPE
    ENTERPRISE  eMylexRaidEventInformation
    VARIABLES   {
	a9EventCode,
	a9ControllerNumber,
	a9EventTimeStamp
    }
          DESCRIPTION
           "Configuration on disk import failed."
           --#SUMMARY  "[ctl: %d :] Configuration on disk import failed." 
           --#ARGUMENTS {1}
           --#SEVERITY MINOR
           --#TIMEINDEX 2
           --#STATE OPERATIONAL
           ::= 805

debugDumpGenerated    TRAP-TYPE
    ENTERPRISE  eMylexRaidEventInformation
    VARIABLES   {
	a9EventCode,
	a9ControllerNumber,
	a9EventTimeStamp
    }
          DESCRIPTION
           "A debug dump exists on this system."
           --#SUMMARY  "[ctl: %d :] A debug dump exists on this system." 
           --#ARGUMENTS {1}
           --#SEVERITY INFORMATIONAL
           --#TIMEINDEX 2
           --#STATE OPERATIONAL
           ::= 806

debugDumpGeneratedPartner    TRAP-TYPE
    ENTERPRISE  eMylexRaidEventInformation
    VARIABLES   {
	a9EventCode,
	a9ControllerNumber,
	a9EventTimeStamp
    }
          DESCRIPTION
           "A debug dump exists on this system."
           --#SUMMARY  "[ctl: %d :] A debug dump exists on this system." 
           --#ARGUMENTS {1}
           --#SEVERITY INFORMATIONAL
           --#TIMEINDEX 2
           --#STATE OPERATIONAL
           ::= 807

cfgCodNotFound    TRAP-TYPE
    ENTERPRISE  eMylexRaidEventInformation
    VARIABLES   {
	a9EventCode,
	a9ControllerNumber,
	a9EventTimeStamp
    }
          DESCRIPTION
           "No valid Configuration On Disk (COD) found."
           --#SUMMARY  "[ctl: %d :] No valid Configuration On Disk (COD) found." 
           --#ARGUMENTS {1}
           --#SEVERITY INFORMATIONAL
           --#TIMEINDEX 2
           --#STATE OPERATIONAL
           ::= 808

cfgCodLunMapNotFound    TRAP-TYPE
    ENTERPRISE  eMylexRaidEventInformation
    VARIABLES   {
	a9EventCode,
	a9ControllerNumber,
	a9EventTimeStamp
    }
          DESCRIPTION
           "No valid SAN map found in Configuration On Disk (COD) found."
           --#SUMMARY  "[ctl: %d :] No valid SAN map found in Configuration On Disk (COD) found." 
           --#ARGUMENTS {1}
           --#SEVERITY INFORMATIONAL
           --#TIMEINDEX 2
           --#STATE OPERATIONAL
           ::= 809

firmwareBoot    TRAP-TYPE
    ENTERPRISE  eMylexRaidEventInformation
    VARIABLES   {
	a9EventCode,
	a9ControllerNumber,
	a9EventTimeStamp
    }
          DESCRIPTION
           "MegaRAID firmware initialization started."
           --#SUMMARY  "[ctl: %d :] MegaRAID firmware initialization started." 
           --#ARGUMENTS {1}
           --#SEVERITY INFORMATIONAL
           --#TIMEINDEX 2
           --#STATE OPERATIONAL
           ::= 810


firmwareCacheConfigMismatch    TRAP-TYPE
    ENTERPRISE  eMylexRaidEventInformation
    VARIABLES   {
	a9EventCode,
	a9ControllerNumber,
	a9EventTimeStamp
    }
          DESCRIPTION
           "Unable to recover cache data from TBBU."
           --#SUMMARY  "[ctl: %d :] Unable to recover cache data from TBBU." 
           --#ARGUMENTS {1}
           --#SEVERITY MAJOR
           --#TIMEINDEX 2
           --#STATE OPERATIONAL
           ::= 811

firmwareCacheProcessed    TRAP-TYPE
    ENTERPRISE  eMylexRaidEventInformation
    VARIABLES   {
	a9EventCode,
	a9ControllerNumber,
	a9EventTimeStamp
    }
          DESCRIPTION
           "Cache data recovered from TBBU successfully."
           --#SUMMARY  "[ctl: %d :] Cache data recovered from TBBU successfully." 
           --#ARGUMENTS {1}
           --#SEVERITY INFORMATIONAL
           --#TIMEINDEX 2
           --#STATE OPERATIONAL
           ::= 812

sasTopologyLoopDetection    TRAP-TYPE
    ENTERPRISE  eMylexRaidEventInformation
    VARIABLES   {
	a9EventCode,
	a9ControllerNumber,
	a9EventTimeStamp
    }
          DESCRIPTION
           "SAS topology error: Loop detected."
           --#SUMMARY  "[ctl: %d :] SAS topology error: Loop detected." 
           --#ARGUMENTS {1}
           --#SEVERITY MAJOR
           --#TIMEINDEX 2
           --#STATE OPERATIONAL
           ::= 960

sasTopologyUnaddressableDevice    TRAP-TYPE
    ENTERPRISE  eMylexRaidEventInformation
    VARIABLES   {
	a9EventCode,
	a9ControllerNumber,
	a9EventTimeStamp
    }
          DESCRIPTION
           "SAS topology error: Unaddressable device."
           --#SUMMARY  "[ctl: %d :] SAS topology error: Unaddressable device." 
           --#ARGUMENTS {1}
           --#SEVERITY MAJOR
           --#TIMEINDEX 2
           --#STATE OPERATIONAL
           ::= 961

sasTopologyMultiplePortsToSameAddr    TRAP-TYPE
    ENTERPRISE  eMylexRaidEventInformation
    VARIABLES   {
	a9EventCode,
	a9ControllerNumber,
	a9EventTimeStamp
    }
          DESCRIPTION
           "SAS topology error: Multiple ports to the same SAS address."
           --#SUMMARY  "[ctl: %d :] SAS topology error: Multiple ports to the same SAS address." 
           --#ARGUMENTS {1}
           --#SEVERITY MAJOR
           --#TIMEINDEX 2
           --#STATE OPERATIONAL
           ::= 962

sasTopologyExpanderError    TRAP-TYPE
    ENTERPRISE  eMylexRaidEventInformation
    VARIABLES   {
	a9EventCode,
	a9ControllerNumber,
	a9EventTimeStamp
    }
          DESCRIPTION
           "SAS topology error: Expander error."
           --#SUMMARY  "[ctl: %d :] SAS topology error: Expander error." 
           --#ARGUMENTS {1}
           --#SEVERITY MAJOR
           --#TIMEINDEX 2
           --#STATE OPERATIONAL
           ::= 963

sasTopologySmpTimeout    TRAP-TYPE
    ENTERPRISE  eMylexRaidEventInformation
    VARIABLES   {
	a9EventCode,
	a9ControllerNumber,
	a9EventTimeStamp
    }
          DESCRIPTION
           "SAS topology error: SMP timeout."
           --#SUMMARY  "[ctl: %d :] SAS topology error: SMP timeout." 
           --#ARGUMENTS {1}
           --#SEVERITY MAJOR
           --#TIMEINDEX 2
           --#STATE OPERATIONAL
           ::= 964

sasTopologyOutOfRouteEntries    TRAP-TYPE
    ENTERPRISE  eMylexRaidEventInformation
    VARIABLES   {
	a9EventCode,
	a9ControllerNumber,
	a9EventTimeStamp
    }
          DESCRIPTION
           "SAS topology error: Out of route entries."
           --#SUMMARY  "[ctl: %d :] SAS topology error: Out of route entries." 
           --#ARGUMENTS {1}
           --#SEVERITY MAJOR
           --#TIMEINDEX 2
           --#STATE OPERATIONAL
           ::= 965

sasTopologyIndexNotFound    TRAP-TYPE
    ENTERPRISE  eMylexRaidEventInformation
    VARIABLES   {
	a9EventCode,
	a9ControllerNumber,
	a9EventTimeStamp
    }
          DESCRIPTION
           "SAS topology error: Index not found."
           --#SUMMARY  "[ctl: %d :] SAS topology error: Index not found." 
           --#ARGUMENTS {1}
           --#SEVERITY MAJOR
           --#TIMEINDEX 2
           --#STATE OPERATIONAL
           ::= 966

sasTopologySmpFunctionFailed    TRAP-TYPE
    ENTERPRISE  eMylexRaidEventInformation
    VARIABLES   {
	a9EventCode,
	a9ControllerNumber,
	a9EventTimeStamp
    }
          DESCRIPTION
           "SAS topology error: SMP functoin failed."
           --#SUMMARY  "[ctl: %d :] SAS topology error: SMP functoin failed." 
           --#ARGUMENTS {1}
           --#SEVERITY MAJOR
           --#TIMEINDEX 2
           --#STATE OPERATIONAL
           ::= 967

sasTopologyCrcError    TRAP-TYPE
    ENTERPRISE  eMylexRaidEventInformation
    VARIABLES   {
	a9EventCode,
	a9ControllerNumber,
	a9EventTimeStamp
    }
          DESCRIPTION
           "SAS topology error: SMP CRC error."
           --#SUMMARY  "[ctl: %d :] SAS topology error: SMP CRC error." 
           --#ARGUMENTS {1}
           --#SEVERITY MAJOR
           --#TIMEINDEX 2
           --#STATE OPERATIONAL
           ::= 968

sasTopologyMultipleSubtractive    TRAP-TYPE
    ENTERPRISE  eMylexRaidEventInformation
    VARIABLES   {
	a9EventCode,
	a9ControllerNumber,
	a9EventTimeStamp
    }
          DESCRIPTION
           "SAS topology error: Multiple subtractive."
           --#SUMMARY  "[ctl: %d :] SAS topology error: Multiple subtractive." 
           --#ARGUMENTS {1}
           --#SEVERITY MAJOR
           --#TIMEINDEX 2
           --#STATE OPERATIONAL
           ::= 969

sasTopologyTableToTable    TRAP-TYPE
    ENTERPRISE  eMylexRaidEventInformation
    VARIABLES   {
	a9EventCode,
	a9ControllerNumber,
	a9EventTimeStamp
    }
          DESCRIPTION
           "SAS topology error: Table to table."
           --#SUMMARY  "[ctl: %d :] SAS topology error: Table to table." 
           --#ARGUMENTS {1}
           --#SEVERITY MAJOR
           --#TIMEINDEX 2
           --#STATE OPERATIONAL
           ::= 970

sasTopologyMultiplePaths    TRAP-TYPE
    ENTERPRISE  eMylexRaidEventInformation
    VARIABLES   {
	a9EventCode,
	a9ControllerNumber,
	a9EventTimeStamp
    }
          DESCRIPTION
           "SAS topology error: Multiple paths."
           --#SUMMARY  "[ctl: %d :] SAS topology error: Multiple paths." 
           --#ARGUMENTS {1}
           --#SEVERITY MAJOR
           --#TIMEINDEX 2
           --#STATE OPERATIONAL
           ::= 971
           
END
