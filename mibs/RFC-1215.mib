----------------------------------------------------------------------------------------------------
-- SIEMENS AG   MIB for MIB Compiler OPC SNMP Server SIMATIC NET
-- RFC-1215.mib
-- RFC  1215
-- Version: 1.0
-- Date: 09.04.2002
-- Comment:
----------------------------------------------------------------------------------------------------
RFC-1215 DEFINITIONS ::= BEGIN


    -- Make builtin items known

    --SMI TRAP-TYPE

          TRAP-TYPE MACRO ::=
          BEGIN
              TYPE NOTATION ::= "ENTERPRISE" value
                                    (enterprise OBJECT IDENTIFIER)
                                VarPart
                                DescrPart
                                ReferPart
              VALUE NOTATION ::= value (VALUE INTEGER)
        
              VarPart ::=
                         "VARIABLES" "{" VarTypes "}"
                              | empty
              VarTypes ::=
                         VarType | VarTypes "," VarType
              VarType ::=
                         value (vartype ObjectName)
        
              DescrPart ::=
                         "DESCRIPTION" value (description DisplayString)
                              | empty
        
              ReferPart ::=
                         "REFERENCE" value (reference DisplayString)
                              | empty
        
          END

END
