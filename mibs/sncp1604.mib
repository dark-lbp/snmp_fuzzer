-- ----------------------------------------------------------------------
-- snCP1604.mib
-- Siemens  SIMATIC NET 
-- CP1604  Private MIB
-- Copyright (c) 2004 Siemens AG
-- ----------------------------------------------------------------------
--
-- MIB Module :   SN-CP1604-PRIV-MIB
--
-- Revision   :   V0.1.0
-- Date       :   2005/03/09 
--
-- ----------------------------------------------------------------------

SN-CP1604-PRIV-MIB DEFINITIONS ::= BEGIN

  IMPORTS
          enterprises FROM RFC1155-SMI
          OBJECT-TYPE FROM RFC-1212;

  DisplayString ::=
    OCTET STRING

siemensAD               OBJECT IDENTIFIER ::= { enterprises 4196 }
adProductMibs           OBJECT IDENTIFIER ::= { siemensAD 1 }
simaticNet              OBJECT IDENTIFIER ::= { adProductMibs 1 }
iCP     	            OBJECT IDENTIFIER ::= { simaticNet 9 } 
iCP1604                 OBJECT IDENTIFIER ::= { iCP 2 } 

-- -------------------------------------------------------------
-- SIMATIC NET CP1604 Objects
-- -------------------------------------------------------------
snCommon             OBJECT IDENTIFIER ::= { iCP1604 1 }
snProductSpecific    OBJECT IDENTIFIER ::= { iCP1604 2 }


-- -------------------------------------------------------------
-- SIMATIC NET CP1604 Report Objects
-- -------------------------------------------------------------
snCP1604Report        OBJECT IDENTIFIER ::= { snProductSpecific 2 }


-- --------------------------------------------------------------
-- SIMATIC NET CP1604 Report Group
-- --------------------------------------------------------------
snCp1604BFLedVal OBJECT-TYPE
   SYNTAX INTEGER { off(1), on(2), blink(3), fastBlink(4) }
   ACCESS read-only
   STATUS mandatory
   DESCRIPTION "State of BF LED. Value list: off(1), on(2), blink(3), fastBlink(4)"
   ::= { snCP1604Report 1 }

snCp1604SFLedVal OBJECT-TYPE
   SYNTAX INTEGER { off(1), on(2), blink(3), fastBlink(4) }
   ACCESS read-only
   STATUS mandatory
   DESCRIPTION "State of SF LED. Value list: off(1), on(2), blink(3), fastBlink(4)"
   ::= { snCP1604Report 2 }

snCp1604RunLedVal OBJECT-TYPE
   SYNTAX INTEGER { off(1), on(2), blink(3), fastBlink(4) }
   ACCESS read-only
   STATUS mandatory
   DESCRIPTION "State of run LED. Value list: off(1), on(2), blink(3), fastBlink(4)"
   ::= { snCP1604Report 3 }

snCp1604StopLedVal OBJECT-TYPE
   SYNTAX INTEGER { off(1), on(2), blink(3), fastBlink(4) }
   ACCESS read-only
   STATUS mandatory
   DESCRIPTION "State of stop LED. Value list: off(1), on(2), blink(3), fastBlink(4)"
   ::= { snCP1604Report 4 }

snCp1604BFLed OBJECT-TYPE
   SYNTAX  DisplayString (SIZE (0..255))
   ACCESS read-only
   STATUS mandatory
   DESCRIPTION "Textual description of the BF LED state"
   ::= { snCP1604Report 5 }

snCp1604SFLed OBJECT-TYPE
   SYNTAX  DisplayString (SIZE (0..255))
   ACCESS read-only
   STATUS mandatory
   DESCRIPTION "Textual description of the SF LED state"
   ::= { snCP1604Report 6 }

snCp1604RunLed OBJECT-TYPE
   SYNTAX  DisplayString (SIZE (0..255))
   ACCESS read-only
   STATUS mandatory
   DESCRIPTION "Textual description of the run LED state"
   ::= { snCP1604Report 7 }

snCp1604StopLed OBJECT-TYPE
   SYNTAX  DisplayString (SIZE (0..255))
   ACCESS read-only
   STATUS mandatory
   DESCRIPTION "Textual description of the stop LED state"
   ::= { snCP1604Report 8 }

END
