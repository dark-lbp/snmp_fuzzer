----------------------------------------------------------------------------------------------------
-- SIEMENS AG   MIB for MIB Compiler OPC SNMP Server SIMATIC NET
-- SN-ELSTP40-PRIV-MIB.mib
-- RFC  
-- Version: 1.2
-- Date: 05.03.2009
-- Comment: Private MIB ELS
----------------------------------------------------------------------------------------------------

-- ----------------------------------------------------------------------
-- snELS.mib
-- SIMATIC NET Industrial Ethernet 
-- ELS Private MIB
-- Copyright (c) 2002 Siemens AG
-- ----------------------------------------------------------------------
--
-- MIB Module :   SN-ELS-PRIV-MIB
--
-- Revision   :   V1.0.0.2
-- Date       :	  2009/03/05 
--
-- ----------------------------------------------------------------------

SN-ELSTP40-PRIV-MIB DEFINITIONS ::= BEGIN

          IMPORTS
                  enterprises, IpAddress, internet, 
                  TimeTicks, Counter FROM RFC1155-SMI

	  			  DisplayString, ifIndex
                         FROM RFC1213-MIB
		
                  OBJECT-TYPE  FROM RFC-1212;

siemensAD               OBJECT IDENTIFIER ::= { enterprises 4196 }
adProductMibs           OBJECT IDENTIFIER ::= { siemensAD 1 }
simaticNet              OBJECT IDENTIFIER ::= { adProductMibs 1 }
iHub                    OBJECT IDENTIFIER ::= { simaticNet 1 }
iSwitch                 OBJECT IDENTIFIER ::= { simaticNet 2 }
iLeanSwitch             OBJECT IDENTIFIER ::= { simaticNet 3 }

-- -------------------------------------------------------------
-- SIMATIC NET OSM/ESM Products
-- These objects are used as sysObjectID of the products.
-- -------------------------------------------------------------
elsTP40M     OBJECT IDENTIFIER ::= { iLeanSwitch 1 }  

-- ************************************************************
--          SIMATIC NET OSM/ESM Private MIB
-- ************************************************************
elsInfo      OBJECT IDENTIFIER ::= { elsTP40M 1 } 
elsStatus    OBJECT IDENTIFIER ::= { elsTP40M 2 }
elsMail      OBJECT IDENTIFIER ::= { elsTP40M 3 }
elsTrap      OBJECT IDENTIFIER ::= { elsTP40M 4 }
elsEvents    OBJECT IDENTIFIER ::= { elsTP40M 5 }  
elsIPInfo    OBJECT IDENTIFIER ::= { elsTP40M 6 }


-- --------------------------------------------------------------
-- SIMATIC NET ELS/OLS Info Group
-- This group contains all common Switch parameters.
-- --------------------------------------------------------------
         version OBJECT-TYPE
              SYNTAX  DisplayString (SIZE (0..62))
              ACCESS  read-only
              STATUS  mandatory
              DESCRIPTION "Firmware Revision"
			       DEFVAL  {"V1.0.0.0"}
              ::= { elsInfo 1 }

          hardware OBJECT-TYPE
              SYNTAX  DisplayString (SIZE (0..62))
              ACCESS  read-only
              STATUS  mandatory
              DESCRIPTION  "Hardware Revision"
			       DEFVAL { "01" }
              ::= { elsInfo 2 }

              
-- --------------------------------------------------------------
-- SIMATIC NET ELS/OLS IP-Info Group
-- This group contains IP-Address related parameters.
-- --------------------------------------------------------------
           
ownIP OBJECT-TYPE 
	SYNTAX  IpAddress 
	ACCESS  read-write
	STATUS  mandatory
	DESCRIPTION "ip address"
	DEFVAL  { 0  }
	::= { elsIPInfo 1 }

netMask OBJECT-TYPE 
	 SYNTAX  IpAddress 
	ACCESS  read-write
	STATUS  mandatory
	 DESCRIPTION "network mask"
	DEFVAL  { 0  }
	::= { elsIPInfo 2 }
               
gateway OBJECT-TYPE 
	SYNTAX  IpAddress 
	ACCESS  read-write
	STATUS  mandatory
	DESCRIPTION "gateway address"
	DEFVAL  { 0  }
	::= { elsIPInfo 3 } 
	
fromDHCP OBJECT-TYPE
	SYNTAX  INTEGER
	ACCESS  read-write
	STATUS  mandatory
	DESCRIPTION "shows if address is from DHCP"
	DEFVAL  { 0 }
	::= { elsIPInfo 4  }

-- --------------------------------------------------------------
-- SIMATIC NET ELS/OLS Email Group
-- This group contains Email related parameters.
-- --------------------------------------------------------------

emailFrom OBJECT-TYPE
	SYNTAX  DisplayString (SIZE (0..62))
	ACCESS  read-write
	STATUS  mandatory
	DESCRIPTION "Mail receiver"
	DEFVAL  {"owner@anywhere.com"}
	::= { elsMail 1 }
			       
emailTo OBJECT-TYPE				   
	SYNTAX  DisplayString (SIZE (0..62))
	ACCESS  read-write
	STATUS  mandatory
	DESCRIPTION "Mail subject"
	DEFVAL  {"test@els.com"}      
	::= { elsMail 2 }
			       			       
emailSubject OBJECT-TYPE
	SYNTAX  DisplayString (SIZE (0..62))
	ACCESS  read-only
	STATUS  mandatory
	DESCRIPTION "Mail Sender"
	DEFVAL  {"test@els.com"}
	::= { elsMail 3 }

smtpdIP OBJECT-TYPE 
	SYNTAX  IpAddress 
	ACCESS  read-write
	STATUS  mandatory
	DESCRIPTION "ip address of smtp Daemon"
	DEFVAL  { 0   }
	::= { elsMail 4 }
			       
-- --------------------------------------------------------------
-- SIMATIC NET ELS/OLS Trap Group
-- This group contains Trap related parameters.
-- --------------------------------------------------------------

trapIP1 OBJECT-TYPE 
	SYNTAX  IpAddress 
	ACCESS  read-write
	STATUS  mandatory
	DESCRIPTION "1. trap receiver's ip address"
	DEFVAL  { 0  }
	::= { elsTrap 1 }

trapIP2 OBJECT-TYPE 
	SYNTAX  IpAddress 
	ACCESS  read-write
	STATUS  mandatory
	DESCRIPTION "2. trap receiver's ip address"
	DEFVAL  { 0   }   
	::= { elsTrap 2 }
               
-- --------------------------------------------------------------
-- SIMATIC NET ELS/OLS Event Group
-- This group contains all the Trap / Email-Event related parameters.
-- --------------------------------------------------------------
emailMask OBJECT-TYPE
	SYNTAX  INTEGER
	ACCESS  read-write
	STATUS  mandatory
	DESCRIPTION "used to mask off Switch-Events to be reported 
	             by mail "
	DEFVAL  { 0 }
	::= { elsEvents 1 }    
	
trapMask OBJECT-TYPE
	SYNTAX  INTEGER
	ACCESS  read-write
	STATUS  mandatory
	DESCRIPTION "used to mask off Switch-events to be reported 
	             by Trap"
	DEFVAL  { 0 }
	::= { elsEvents 2 }

otherMask OBJECT-TYPE
	SYNTAX  INTEGER
	ACCESS  read-write
	STATUS  mandatory
	DESCRIPTION "used to mask off PST-Request or Power-On events to be reported 
	             by Trap or Email"
	DEFVAL  { 0 }
	::= { elsEvents 3 }
	
-- --------------------------------------------------------------
-- SIMATIC NET ELS/OLS Status Group
-- This group contains switch related parameters.
-- --------------------------------------------------------------  
receiveError1 OBJECT-TYPE
	SYNTAX  INTEGER
	ACCESS  read-only
	STATUS  mandatory
	DESCRIPTION "number of receive errors of port 1"
	DEFVAL  { 0 }
	::= { elsStatus 1 }      

receiveError2 OBJECT-TYPE
	SYNTAX  INTEGER
	ACCESS  read-only
	STATUS  mandatory
	DESCRIPTION "number of receive errors of port 2"
	DEFVAL  { 0 }
	::= { elsStatus 2 }      

receiveError3 OBJECT-TYPE
	SYNTAX  INTEGER
	ACCESS  read-only
	STATUS  mandatory
	DESCRIPTION "number of receive errors of port 3"
	DEFVAL  { 0 }
	::= { elsStatus 3 }      

receiveError4 OBJECT-TYPE
	SYNTAX  INTEGER
	ACCESS  read-only
	STATUS  mandatory
	DESCRIPTION "number of receive errors of port 4"
	DEFVAL  { 0 }
	::= { elsStatus 4 }      

collisionCount1 OBJECT-TYPE
	SYNTAX  INTEGER
	ACCESS  read-only
	STATUS  mandatory
	DESCRIPTION "number of collisions of port 1"
	DEFVAL  { 0 }
	::= { elsStatus 5 } 
	
collisionCount2 OBJECT-TYPE
	SYNTAX  INTEGER
	ACCESS  read-only
	STATUS  mandatory
	DESCRIPTION "number of collisions of port 2"
	DEFVAL  { 0 }
	::= { elsStatus 6 }

collisionCount3 OBJECT-TYPE
	SYNTAX  INTEGER
	ACCESS  read-only
	STATUS  mandatory
	DESCRIPTION "number of collisions of port 3"
	DEFVAL  { 0 }
	::= { elsStatus 7 } 
	
collisionCount4 OBJECT-TYPE
	SYNTAX  INTEGER
	ACCESS  read-only
	STATUS  mandatory
	DESCRIPTION "number of collisions of port 4"
	DEFVAL  { 0 }
	::= { elsStatus 8 }
          
ledStatus OBJECT-TYPE
	SYNTAX  INTEGER
	ACCESS  read-only
	STATUS  mandatory
	DESCRIPTION "reflects LEDs of switch"
	DEFVAL  { 0 }
	::= { elsStatus 9 }         

startBank OBJECT-TYPE
	SYNTAX  INTEGER
	ACCESS  read-only
	STATUS  mandatory
	DESCRIPTION "shows startBank "
	DEFVAL  { 0 }
	::= { elsStatus 10 }
	
-- --------------------------------------------------------------
-- SIMATIC NET ELS/OLS Email Group
-- This group contains Email related parameters.
-- --------------------------------------------------------------
        
      
          -- ELS	  



          END
